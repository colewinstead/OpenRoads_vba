Attribute VB_Name = "ModDel_Title_BLK_TX"
Sub BmrDel_Title_BLK_TX()
    Dim startPoint As Point3d
    Dim point As Point3d, point2 As Point3d
    Dim lngTemp As Long
    Dim oMessage As CadInputMessage

'   Send a keyin that can be a command string
    CadInputQueue.SendKeyin "OF=""XS_X_FINAL"";SELVIEW 1"

    CadInputQueue.SendKeyin "OF=""Default"";SELVIEW 1"

    CadInputQueue.SendKeyin "OF=""SHEET_TITLE_BLOCK"";SELVIEW 1"

    CadInputQueue.SendKeyin "OF=""SHEET_PRELIM"";SELVIEW 1"

    CadInputQueue.SendKeyin "OF=""SHEET_PLOTTING_SHAPE"";SELVIEW 1"

    CadInputQueue.SendKeyin "OF=""SHEET_MDOT_LOGO"";SELVIEW 1"

    CadInputQueue.SendKeyin "OF=""SHEET_LOGO"";SELVIEW 1"

    CadInputQueue.SendKeyin "OF=""SHEET_CONSULTANT_STAMP"";SELVIEW 1"

    CadInputQueue.SendKeyin "OF=""SHEET_BORDER"";SELVIEW 1"

    CadInputQueue.SendKeyin "OF=""Draft_Named_Boundary"";SELVIEW 1"

'   Start a command
    CadInputQueue.SendCommand "DELETE ELEMENT"

'   Send a tentative point
'   Coordinates are in master units
    CadInputQueue.SendTentativePoint Point3dFromXYZ(2.66828351686551, 1.05610253733788, 0#), 1

'   Coordinates are in master units
    startPoint.X = 2.66409166666667
    startPoint.Y = 1.00483299993267
    startPoint.Z = 0#

'   Send a data point to the current command
    point.X = startPoint.X
    point.Y = startPoint.Y
    point.Z = startPoint.Z
    CadInputQueue.SendAdjustedDataPoint point, 1

    CadInputQueue.SendTentativePoint Point3dFromXYZ(2.70226122008101, 1.03400792507503, 0#), 1

    point.X = startPoint.X + 3.59388888888881E-02
    point.Y = startPoint.Y + 6.6613E-16
    point.Z = startPoint.Z
    CadInputQueue.SendAdjustedDataPoint point, 1

    CadInputQueue.SendTentativePoint Point3dFromXYZ(2.73623892329651, 1.02041124060558, 0#), 1

    point.X = startPoint.X + 7.18777777777757E-02
    point.Y = startPoint.Y + 4.4409E-16
    point.Z = startPoint.Z
    CadInputQueue.SendAdjustedDataPoint point, 1

    CadInputQueue.SendTentativePoint Point3dFromXYZ(2.77021662651202, 1.01531248392953, 0#), 1

    point.X = startPoint.X + 0.107816666666665
    point.Y = startPoint.Y + 2.2204E-16
    point.Z = startPoint.Z
    CadInputQueue.SendAdjustedDataPoint point, 1

    CadInputQueue.SendTentativePoint Point3dFromXYZ(2.67168128718706, 0.792666775742297, 0#), 1

    point.X = startPoint.X + 5.20833333333215E-03
    point.Y = startPoint.Y - 0.250293749102142
    point.Z = startPoint.Z
    CadInputQueue.SendAdjustedDataPoint point, 1

    CadInputQueue.SendTentativePoint Point3dFromXYZ(2.71415341620644, 0.821559730239877, 0#), 1

    point.X = startPoint.X + 0.053908333333331
    point.Y = startPoint.Y - 0.215062861071253
    point.Z = startPoint.Z
    CadInputQueue.SendAdjustedDataPoint point, 1

    CadInputQueue.SendTentativePoint Point3dFromXYZ(2.76851774135124, 0.772271749038122, 0#), 1

    point.X = startPoint.X + 0.102608333333332
    point.Y = startPoint.Y - 0.259625023233415
    point.Z = startPoint.Z
    CadInputQueue.SendAdjustedDataPoint point, 1

    CadInputQueue.SendTentativePoint Point3dFromXYZ(2.66828351686551, 0.685592885545382, 0#), 1

    point.X = startPoint.X + 5.20833333333215E-03
    point.Y = startPoint.Y - 0.346638150646543
    point.Z = startPoint.Z
    CadInputQueue.SendAdjustedDataPoint point, 1

    CadInputQueue.SendTentativePoint Point3dFromXYZ(2.71925007168876, 0.690691642221425, 0#), 1

    point.X = startPoint.X + 0.053908333333331
    point.Y = startPoint.Y - 0.346638150646543
    point.Z = startPoint.Z
    CadInputQueue.SendAdjustedDataPoint point, 1

    CadInputQueue.SendTentativePoint Point3dFromXYZ(2.76851774135124, 0.688992056662744, 0#), 1

    point.X = startPoint.X + 0.102608333333332
    point.Y = startPoint.Y - 0.346638150646542
    point.Z = startPoint.Z
    CadInputQueue.SendAdjustedDataPoint point, 1

    CadInputQueue.SendKeyin "ON=""Default"";SELVIEW 1"

    CadInputQueue.SendKeyin "ON=""SHEET_TITLE_BLOCK"";SELVIEW 1"

    CadInputQueue.SendKeyin "ON=""SHEET_PRELIM"";SELVIEW 1"

    CadInputQueue.SendKeyin "ON=""SHEET_PLOTTING_SHAPE"";SELVIEW 1"

    CadInputQueue.SendKeyin "ON=""SHEET_MDOT_LOGO"";SELVIEW 1"

    CadInputQueue.SendKeyin "ON=""SHEET_LOGO"";SELVIEW 1"

    CadInputQueue.SendKeyin "ON=""SHEET_CONSULTANT_STAMP"";SELVIEW 1"

    CadInputQueue.SendKeyin "ON=""SHEET_BORDER"";SELVIEW 1"

    CadInputQueue.SendKeyin "ON=""Draft_Named_Boundary"";SELVIEW 1"

    CommandState.StartDefaultCommand
End Sub
Sub BmrDel_Title_BLK_TX_AllSheets()

    Dim oModel As ModelReference

    ' Loop through all models in the active DGN
    For Each oModel In ActiveDesignFile.Models

        ' Only run on sheet models
        If oModel.Type = msdModelTypeSheet Then

            oModel.Activate  ' make this sheet active

            ' Call the recorded macro that edits the field on this sheet
            BmrDel_Title_BLK_TX

        End If

    Next oModel

    ' Save settings after all changes
    CadInputQueue.SendCommand "FILEDESIGN SAVESETTINGS"

    MsgBox "Finished deleting default Title Block Text.", vbInformation

End Sub
