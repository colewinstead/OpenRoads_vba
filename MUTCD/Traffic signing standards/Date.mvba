Attribute VB_Name = "Module1"
Option Explicit

Private Const RD3_MODEL As String = "Default"
Private Const RD3_DATE As String = "12/23/25"

Private Const RD3_INTERACTIVE As Boolean = True   ' set False for Batch
Private Const RD3_X_NUDGE As Double = 0#
Private Const RD3_Y_NUDGE As Double = 0#
Private Const RD3_ROTATE_CLOCKWISE As Boolean = False
Private Const RD3_DELETE_EXISTING As Boolean = True

Public Sub RD3_PlaceDate_FromUpdatedText()
    On Error GoTo EH

    If RD3_ModelExists(RD3_MODEL) Then
        ActiveDesignFile.Models(RD3_MODEL).Activate
    End If

    Dim msg As String
    msg = RD3_DoPlace(RD3_DATE)

    ActiveDesignFile.Save
    If RD3_INTERACTIVE Then MsgBox msg, vbInformation, "Revision Date Macro"
    Exit Sub

EH:
    If RD3_INTERACTIVE Then MsgBox "ERROR: " & Err.Number & vbCrLf & Err.Description, vbCritical, "Revision Date Macro"
    Debug.Print "ERROR: " & ActiveDesignFile.Name & " | " & Err.Number & " | " & Err.Description
End Sub

Private Function RD3_DoPlace(ByVal dateStr As String) As String
    Dim eUpdated As Element
    Dim eDateLbl As Element

    ' UPDATED TEXT. anchor (column)
    Set eUpdated = RD3_FindTextMostVertical_ByKeywords(Array("UPDATED", "TEXT"))
    If eUpdated Is Nothing Then
        RD3_DoPlace = "SKIP: Could not find a text element containing UPDATED + TEXT in '" & ActiveModelReference.Name & "'."
        Exit Function
    End If

    ' DATE anchor (row)
    Set eDateLbl = RD3_FindTextMostVertical_ByKeywords(Array("DATE"))
    If eDateLbl Is Nothing Then
        RD3_DoPlace = "SKIP: Could not find a vertical DATE text element in '" & ActiveModelReference.Name & "'."
        Exit Function
    End If

    Dim rU As Range3d, rD As Range3d
    rU = eUpdated.Range
    rD = eDateLbl.Range

    Dim targetPt As Point3d
    targetPt = Point3dFromXYZ( _
        (rU.Low.X + rU.High.X) / 2# + RD3_X_NUDGE, _
        (rD.Low.y + rD.High.y) / 2# + RD3_Y_NUDGE, _
        0#)

    Dim approxH As Double
    approxH = Abs(rU.High.y - rU.Low.y)
    If approxH <= 0# Then approxH = 1#

    If RD3_DELETE_EXISTING Then
        RD3_DeleteDateLikeNear targetPt, approxH
    End If

    ' Make 90° rotation matrix (so text is created vertical—no rotate method needed)
    Dim rot As Matrix3d
    rot = RD3_MakeRot90(RD3_ROTATE_CLOCKWISE)

    ' Create rotated date
    Dim tNew As TextElement
    Set tNew = CreateTextElement1(Nothing, dateStr, targetPt, rot)

    ' Match symbology to UPDATED TEXT.
    tNew.Level = eUpdated.Level
    tNew.Color = eUpdated.Color
    tNew.LineWeight = eUpdated.LineWeight

    ' Try to match font/height/width if your build exposes them (safe late-bound)
    RD3_CopyTextSizingLate eUpdated, tNew

    ' Center on target
    RD3_CenterOnPoint tNew, targetPt

    ActiveModelReference.AddElement tNew
    RD3_DoPlace = "OK: Placed " & dateStr & " using UPDATED TEXT + DATE anchors."
End Function

' -------- Find most vertical text that contains keywords --------
Private Function RD3_FindTextMostVertical_ByKeywords(ByVal keywords As Variant) As Element
    Dim esc As ElementScanCriteria
    Set esc = New ElementScanCriteria
    esc.ExcludeAllTypes
    esc.IncludeType msdElementTypeText

    Dim ee As ElementEnumerator
    Set ee = ActiveModelReference.Scan(esc)

    Dim best As Element
    Dim bestScore As Double: bestScore = -1#
    Dim bestX As Double: bestX = 9E+99

    Do While ee.MoveNext
        Dim e As Element: Set e = ee.Current

        Dim raw As String
        raw = RD3_GetText(e)

        Dim norm As String
        norm = RD3_Normalize(raw)

        If RD3_ContainsAll(norm, keywords) Then
            Dim r As Range3d: r = e.Range
            Dim w As Double: w = Abs(r.High.X - r.Low.X)
            Dim h As Double: h = Abs(r.High.y - r.Low.y)

            Dim score As Double
            If w > 0# Then score = h / w Else score = 0#

            ' tie-breaker: prefer more vertical, then more left
            If (score > bestScore) Or (Abs(score - bestScore) < 0.0001 And r.Low.X < bestX) Then
                bestScore = score
                bestX = r.Low.X
                Set best = e
            End If
        End If
    Loop

    Set RD3_FindTextMostVertical_ByKeywords = best
End Function

' -------- Read text (late-bound, works with your odd VBA build) --------
Private Function RD3_GetText(ByVal e As Element) As String
    Dim o As Object: Set o = e
    On Error Resume Next

    RD3_GetText = ""
    RD3_GetText = CStr(o.Text)
    If Err.Number = 0 And Len(RD3_GetText) > 0 Then Exit Function
    Err.Clear

    RD3_GetText = CStr(o.TextString)
    If Err.Number <> 0 Then
        Err.Clear
        RD3_GetText = ""
    End If
End Function

' -------- Normalize strings so "UPDATED TEXT." always matches --------
Private Function RD3_Normalize(ByVal s As String) As String
    s = UCase$(s)

    s = Replace$(s, vbCr, " ")
    s = Replace$(s, vbLf, " ")
    s = Replace$(s, vbTab, " ")
    s = Replace$(s, Chr$(160), " ") ' NBSP

    ' Remove punctuation that often breaks exact matches
    s = Replace$(s, ".", " ")
    s = Replace$(s, ",", " ")
    s = Replace$(s, ":", " ")
    s = Replace$(s, ";", " ")

    ' Collapse multiple spaces
    Do While InStr(s, "  ") > 0
        s = Replace$(s, "  ", " ")
    Loop

    RD3_Normalize = Trim$(s)
End Function

Private Function RD3_ContainsAll(ByVal hay As String, ByVal keywords As Variant) As Boolean
    Dim i As Long
    For i = LBound(keywords) To UBound(keywords)
        If InStr(1, hay, CStr(keywords(i)), vbTextCompare) = 0 Then
            RD3_ContainsAll = False
            Exit Function
        End If
    Next i
    RD3_ContainsAll = True
End Function

' -------- Rotation matrix 90° about Z --------
Private Function RD3_MakeRot90(ByVal clockwise As Boolean) As Matrix3d
    Dim m As Matrix3d
    m = Matrix3dIdentity

    If clockwise Then
        m.RowX = Point3dFromXYZ(0#, 1#, 0#)
        m.RowY = Point3dFromXYZ(-1#, 0#, 0#)
    Else
        m.RowX = Point3dFromXYZ(0#, -1#, 0#)
        m.RowY = Point3dFromXYZ(1#, 0#, 0#)
    End If

    m.RowZ = Point3dFromXYZ(0#, 0#, 1#)
    RD3_MakeRot90 = m
End Function

' -------- Copy font/height/width (safe) --------
Private Sub RD3_CopyTextSizingLate(ByVal src As Element, ByVal dst As TextElement)
    Dim oS As Object: Set oS = src
    Dim oD As Object: Set oD = dst
    On Error Resume Next
    oD.FONTNAME = oS.FONTNAME
    oD.Height = oS.Height
    oD.Width = oS.Width
    Err.Clear
End Sub

' -------- Center element on point (late-bound Move) --------
Private Sub RD3_CenterOnPoint(ByVal e As Element, ByRef pt As Point3d)
    Dim r As Range3d
    r = e.Range

    Dim cx As Double, cy As Double
    cx = (r.Low.X + r.High.X) / 2#
    cy = (r.Low.y + r.High.y) / 2#

    Dim v As Vector3d
    v = Vector3dFromXYZ(pt.X - cx, pt.y - cy, 0#)

    Dim o As Object: Set o = e
    On Error Resume Next
    CallByName o, "Move", VbMethod, v
    Err.Clear
End Sub

' -------- Delete existing date-like text near target (no .Delete dependency) --------
Private Sub RD3_DeleteDateLikeNear(ByRef pt As Point3d, ByVal approxH As Double)
    Dim halfW As Double: halfW = approxH * 0.2
    Dim halfH As Double: halfH = approxH * 0.2

    Dim esc As ElementScanCriteria
    Set esc = New ElementScanCriteria
    esc.ExcludeAllTypes
    esc.IncludeType msdElementTypeText

    Dim ee As ElementEnumerator
    Set ee = ActiveModelReference.Scan(esc)

    Do While ee.MoveNext
        Dim e As Element: Set e = ee.Current
        Dim s As String: s = RD3_GetText(e)

        If (s Like "##/##/##") Or (s Like "##/##/####") Then
            Dim r As Range3d: r = e.Range
            Dim cx As Double: cx = (r.Low.X + r.High.X) / 2#
            Dim cy As Double: cy = (r.Low.y + r.High.y) / 2#

            If Abs(cx - pt.X) <= halfW And Abs(cy - pt.y) <= halfH Then
                RD3_DeleteElementLate e
            End If
        End If
    Loop
End Sub

Public Sub RD3_Debug_ListUpdated()
    Dim esc As ElementScanCriteria: Set esc = New ElementScanCriteria
    esc.ExcludeAllTypes
    esc.IncludeType msdElementTypeText

    Dim ee As ElementEnumerator: Set ee = ActiveModelReference.Scan(esc)
    Dim out As String: out = ""

    Do While ee.MoveNext
        Dim s As String
        s = RD3_GetText(ee.Current)
        If InStr(1, UCase$(s), "UPDATED", vbTextCompare) > 0 Then
            out = out & "[" & s & "]" & vbCrLf
        End If
    Loop

    If Len(out) = 0 Then out = "No text elements returned the word UPDATED via RD3_GetText()."
    MsgBox out
End Sub


Private Sub RD3_DeleteElementLate(ByVal e As Element)
    On Error Resume Next
    Dim oE As Object: Set oE = e
    CallByName oE, "Delete", VbMethod
    If Err.Number = 0 Then Exit Sub
    Err.Clear

    Dim oM As Object: Set oM = ActiveModelReference
    CallByName oM, "RemoveElement", VbMethod, e
    Err.Clear
End Sub

Private Function RD3_ModelExists(ByVal modelName As String) As Boolean
    On Error GoTo Nope
    Dim m As ModelReference
    Set m = ActiveDesignFile.Models(modelName)
    RD3_ModelExists = True
    Exit Function
Nope:
    RD3_ModelExists = False
End Function
