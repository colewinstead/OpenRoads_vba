Attribute VB_Name = "ProgramInfo"
'--------------------------------------------------------------------------------------------------
'   VBA - Rotate to Horizontal
'
'   Name:   RotateElementHorizontal.mvba
'
'   Description:    This program rotates elements horizontal to the view. It is normally used for
'                   clean up of notes, labels etc. to appear horizontal on plan sheets.
'
'                   When the command is started the user is prompted to Identify Element. The element's
'                   attributes are read and the appropriate rotation angle is applied.
'
'                   This program supports the following element types: lines, line strings, shapes,
'                   text, text nodes, ellipses, arcs, cells, shared cells, shared cell definitions,
'                   tags, cones.
'
'                   For line strings and shapes the nearest segment is used to control the angle. For
'                   these elements as well as lines the smallest angle of rotation is utilized.
'
'                   If the chosen element is a in a graphic group and the graphic group lock is on then
'                   the rotation from the element chosen is applied to all members of the group.
'
'
'
'   Written:        01/12/2005
'
'   Revised:
'
'
'
'
'
'--------------------------------------------------------------------------------------------------

Attribute VB_Name = "RotateElementHoriz"

Option Explicit

Sub Main()

    CommandState.StartLocate New clsRotateElementHoriz
    
    
End Sub

Attribute VB_Name = "clsRotateElementHoriz"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False

Option Explicit

Implements ILocateCommandEvents
Private IDpoint As Point3d


Function GetAngleFrom2Points(pt1 As Point3d, pt2 As Point3d) As Double

    Dim vec1 As Vector3d, vec2 As Vector3d
    Dim angle As Double
    
    'get vectors
    vec1 = Vector3dSubtractPoint3dPoint3d(pt2, pt1)
    
    vec2 = Vector3dFromXY(1#, 0#)
    
    'duplicate keyin logic
    angle = Degrees(Vector3dAngleBetweenVectorsXY(vec2, vec1))
    If angle < 0# Then
        angle = angle + 360#
    End If
    
    GetAngleFrom2Points = angle
End Function

Sub RotateGG(gg As Long, AdjustmentAngle As Double)

    Dim currentElement As Element
    
    Dim GGScanCriteria As ElementScanCriteria
    Set GGScanCriteria = New ElementScanCriteria

    GGScanCriteria.IncludeOnlyGraphicGroup gg
  
    '  Now that the ElementScanCriteria object has been set
    '  up, use it to scan.  The Scan method returns
    '  an ElementEnumerator object that can be used
    '  to step through the elements that satisfy the scan
    '  criteria.
    
    Dim GGScanEnumerator As ElementEnumerator
    Set GGScanEnumerator = ActiveModelReference.Scan(GGScanCriteria)

    CadInputQueue.SendCommand "Mark"
    ShowStatus "Processing Graphic Group"

    '  Calling MoveNext the first time positions the enumerator
    '  to the first element.  Subsequent calls advance it by one.
    '  MoveNext returns False when it advances beyond the last
    '  element.
    Do While GGScanEnumerator.MoveNext
    
        Set currentElement = GGScanEnumerator.Current

        ' erase, rotate, rewrite & redraw element
        currentElement.Redraw msdDrawingModeErase
        currentElement.Rotate IDpoint, 0, 0, AdjustmentAngle
        currentElement.Rewrite
        currentElement.Redraw
        
    Loop
    
    ShowStatus " "

    CommandState.StartLocate New clsRotateElementHoriz

End Sub



Private Sub ILocateCommandEvents_Accept(ByVal Element As Element, Point As Point3d, ByVal View As View)
    
    Dim ElementAngle As Double
    Dim viewAngle As Double
    Dim AdjustmentAngle As Double
    Dim GetRotation As Matrix3d
    Dim mtrxRotation As Matrix3d
    Dim beginvertex  As Long
    Dim endvertex As Long
    Dim Angle1 As Double
    Dim Angle2 As Double
    Dim status As String
    Dim DoNotProcess As Integer

    DoNotProcess = 0
    If Not Matrix3dIsXYRotation(View.Rotation, viewAngle) Then
    
        viewAngle = Radians(0)
            
    End If
    
    
    '  Start the NULL command so that UNDO does not
    '  combine this operation with some other operation
    CadInputQueue.SendCommand "NULL"
    
    If Element.IsLineElement Then
    
        Dim LinePoints() As Point3d
        Dim numberofvertices As Integer
        
        LinePoints() = Element.AsLineElement.ConstructVertexList(0.0001)
        numberofvertices = Element.AsLineElement.VerticesCount
        
        'line string
        If numberofvertices > 2 Then
        
            beginvertex = Element.AsLineElement.GetClosestSegment(IDpoint)
            endvertex = beginvertex + 1
        
            Angle1 = Radians(GetAngleFrom2Points(LinePoints(beginvertex), LinePoints(endvertex)))
            Angle2 = Radians(GetAngleFrom2Points(LinePoints(endvertex), LinePoints(beginvertex)))
            
        'line
        Else
        
            Angle1 = Radians(GetAngleFrom2Points(LinePoints(0), LinePoints(1)))
            Angle2 = Radians(GetAngleFrom2Points(LinePoints(1), LinePoints(0)))
            
        End If
        
        ' get smallest angle
        If (Angle1 < Angle2 And Angle2 < Radians(270)) Or (Angle1 > Angle2 And Angle1 > Radians(270)) Then
        
            ElementAngle = Angle1
            
        Else
            
            ElementAngle = Angle2
        
        End If
        
    ElseIf Element.IsShapeElement Then
    
        Dim ShapeCorners() As Point3d
       
        ShapeCorners() = Element.AsShapeElement.ConstructVertexList(0.0001)
        beginvertex = Element.AsShapeElement.GetClosestSegment(IDpoint)
        endvertex = beginvertex + 1
        
        Angle1 = Radians(GetAngleFrom2Points(ShapeCorners(beginvertex), ShapeCorners(endvertex)))
        Angle2 = Radians(GetAngleFrom2Points(ShapeCorners(endvertex), ShapeCorners(beginvertex)))
        
        ' get smallest angle
        If (Angle1 < Angle2 And Angle2 < Radians(270)) Or (Angle1 > Angle2 And Angle1 > Radians(270)) Then
        
            ElementAngle = Angle1
            
        Else
            
            ElementAngle = Angle2
        
        End If
        
    
    ' elements using rotation matrix
    Else
    
        If Element.IsEllipticalElement Then
    
            '  Both Arcs and Ellipse
            GetRotation = Element.AsEllipticalElement.Rotation
        
        ElseIf Element.IsCellElement Then
    
            GetRotation = Element.AsCellElement.Rotation
        
        ElseIf Element.IsConeElement Then
    
            GetRotation = Element.AsConeElement.Rotation
    
        ElseIf Element.IsTextElement Then
    
            GetRotation = Element.AsTextElement.Rotation
        
        ElseIf Element.IsTextNodeElement Then
    
            GetRotation = Element.AsTextNodeElement.Rotation
        
        ElseIf Element.IsSharedCellElement Then
    
            GetRotation = Element.AsSharedCellElement.Rotation
        
        ElseIf Element.IsSharedCellDefinitionElement Then
    
            GetRotation = Element.AsSharedCellDefinitionElement.Rotation
        
        ElseIf Element.IsTagElement Then
    
            GetRotation = Element.AsTagElement.Rotation
        
        'invalid element type
        Else
        
             status = MsgBox("Sorry ... that element type is not supported by this program", 0, "Invalid Element")
             If status = vbOK Then
                
                DoNotProcess = 1
                
            End If
        
        End If
        
        'extract angle about Z axis from matrix3d
        
        If Not Matrix3dIsXYRotation(GetRotation, ElementAngle) Then
    
            ElementAngle = Radians(0)
        
        End If
    
    End If
    
    
    'calculate adjustment angle
    
    AdjustmentAngle = viewAngle - (Radians(360) - ElementAngle)
    
    If AdjustmentAngle <= Radians(180) Then
        
            While AdjustmentAngle <= Radians(-180)
            
                AdjustmentAngle = AdjustmentAngle + Radians(360)
                
            Wend
            
    ElseIf AdjustmentAngle > Radians(180) Then
            
            While AdjustmentAngle > Radians(180)
            
                AdjustmentAngle = AdjustmentAngle - Radians(360)
                
            Wend
            
    End If
    
    'final adjustment to set rotation needed
    AdjustmentAngle = Radians(0) - AdjustmentAngle
    
    ' trap for graphic groups
    If Element.GraphicGroup > 0 And ActiveSettings.GraphicGroupLockEnabled = True And DoNotProcess = 0 Then
        
        Call RotateGG(Element.GraphicGroup, AdjustmentAngle)
        
    'Single Valid Elements
    ElseIf DoNotProcess = 0 Then
    
        ' erase, rotate, rewrite & redraw element
        Element.Redraw msdDrawingModeErase
    
        Element.Rotate IDpoint, 0, 0, AdjustmentAngle
    
        Element.Rewrite
        Element.Redraw

        CommandState.StartLocate New clsRotateElementHoriz
    
    End If
    
    ' restart for invalid elements
    If DoNotProcess = 1 Then
    
        CommandState.StartLocate New clsRotateElementHoriz
        
    End If
    
End Sub

Private Sub ILocateCommandEvents_Cleanup()



End Sub

Private Sub ILocateCommandEvents_Dynamics(Point As Point3d, ByVal View As View, ByVal DrawMode As MsdDrawingMode)
    
End Sub

Private Sub ILocateCommandEvents_LocateFailed()

    ShowStatus "Element not Found!"
    CommandState.StartLocate New clsRotateElementHoriz
    
End Sub

Private Sub ILocateCommandEvents_LocateFilter(ByVal Element As Element, Point As Point3d, Accepted As Boolean)
  
    ShowPrompt "Accept/Reject"
    IDpoint = Point
            
         
End Sub

Private Sub ILocateCommandEvents_LocateReset()

    CommandState.StartLocate New clsRotateElementHoriz
    
End Sub

Private Sub ILocateCommandEvents_Start()

    Dim lc As LocateCriteria
    
    '  Since this command does modify the original element,
    '  set the locate criteria to allow only writable elements.
    Set lc = CommandState.CreateLocateCriteria(True)
    CommandState.SetLocateCriteria lc
    
    
    ShowCommand "Rotate to Horizontal"
    ShowPrompt "Identify Element"
End Sub
