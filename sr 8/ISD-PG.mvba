Attribute VB_Name = "ModISD_PG"
Sub BmrISD_PG()
    Dim startPoint As Point3d
    Dim point As Point3d, point2 As Point3d
    Dim lngTemp As Long
    Dim oMessage As CadInputMessage

'   Start a command
    CadInputQueue.SendCommand "TEXTEDITOR MODIFY"

'   Send a tentative point
'   Coordinates are in master units
    CadInputQueue.SendTentativePoint Point3dFromXYZ(2.72639069223222, 0.107503663420974, 0#), 1

'   Coordinates are in master units
    startPoint.X = 2.71801666666667
    startPoint.Y = 0.106315876158204
    startPoint.Z = 0#

'   Send a data point to the current command
    point.X = startPoint.X
    point.Y = startPoint.Y
    point.Z = startPoint.Z
    CadInputQueue.SendAdjustedDataPoint point, 1

'   XX-MacroComment_Header-XX

'   XX-MacroComment_InsertText-XX

'   Send a keyin that can be a command string
    CadInputQueue.SendKeyin "TEXTEDITOR PLAYCOMMAND INSERT_TEXT ""isd"""

'   XX-MacroComment_KeyDownPerCharacter-XX

    CadInputQueue.SendCommand "TEXTEDITOR PLAYCOMMAND KEY_DOWN KEY_CODE 0x02 CONTROL_KEY_STATE UP SHIFT_KEY_STATE UP ALT_KEY_STATE UP"

'   XX-MacroComment_KeyDownPerCharacter-XX

    CadInputQueue.SendCommand "TEXTEDITOR PLAYCOMMAND KEY_DOWN KEY_CODE 0x02 CONTROL_KEY_STATE UP SHIFT_KEY_STATE UP ALT_KEY_STATE UP"

'   XX-MacroComment_KeyDownPerCharacter-XX

    CadInputQueue.SendCommand "TEXTEDITOR PLAYCOMMAND KEY_DOWN KEY_CODE 0x02 CONTROL_KEY_STATE UP SHIFT_KEY_STATE UP ALT_KEY_STATE UP"

    CadInputQueue.SendKeyin "TEXTEDITOR PLAYCOMMAND INSERT_TEXT ""ISD-  """

    point.X = startPoint.X - 2.4212796608456E-03
    point.Y = startPoint.Y + 0.06362773829981
    point.Z = startPoint.Z
    CadInputQueue.SendDataPoint point, 1

    CadInputQueue.SendTentativePoint Point3dFromXYZ(2.71090177603782, 5.82089652338371E-02, 0#), 1

    point.X = startPoint.X + 1.00000000010869E-04
    point.Y = startPoint.Y - 4.86999999999994E-02
    point.Z = startPoint.Z
    CadInputQueue.SendAdjustedDataPoint point, 1

    point.X = startPoint.X + 3.98788071753478E-02
    point.Y = startPoint.Y - 8.80919725453871E-04
    point.Z = startPoint.Z
    CadInputQueue.SendDataPoint point, 1

    CommandState.StartDefaultCommand
End Sub
Sub Wrapper_AllSheets()

    Dim oModel As ModelReference

    ' Loop through all models in the active DGN
    For Each oModel In ActiveDesignFile.Models

        ' Only run on sheet models
        If oModel.Type = msdModelTypeSheet Then

            oModel.Activate   ' make this sheet active

            ' Call the recorded macro that does the delete on this sheet
            BmrISD_PG

        End If

    Next oModel

    ' Save settings after all changes
    CadInputQueue.SendCommand "FILEDESIGN SAVESETTINGS"

    MsgBox "Finished changing the title on all sheet models.", vbInformation

End Sub
