Attribute VB_Name = "ModMUTCD_DATE_CHNG2"
Option Explicit

Sub ReplaceDate_InFields_1215_to_1218()
    Dim findStr As String, repStr As String
    findStr = "12/18/25"
    repStr = "12/23/25"

    ' Load Find/Replace Text tool silently and set the strings
    CadInputQueue.SendCommand "MDL SILENTLOAD FINDREPLACETEXT,CHNGTXT CHANGE DIALOGTEXT"
    CadInputQueue.SendKeyin "FIND DIALOG SEARCHSTRING " & findStr & "; FIND DIALOG REPLACESTRING " & repStr

    ' Replace everything it found
    CadInputQueue.SendKeyin "CHANGE TEXT ALLFILTERED"
End Sub
