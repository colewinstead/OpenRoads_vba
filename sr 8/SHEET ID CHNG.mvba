Attribute VB_Name = "ModSHEET_ID_CHNG"
Sub BmrSHEET_ID_CHNG()
    Dim startPoint As Point3d
    Dim point As Point3d, point2 As Point3d
    Dim lngTemp As Long
    Dim oMessage As CadInputMessage

'   Start a command
    CadInputQueue.SendCommand "TEXTEDITOR MODIFY"

'   Send a tentative point
'   Coordinates are in master units
    CadInputQueue.SendTentativePoint Point3dFromXYZ(2.72469103628331, 0.105760211432709, 0#), 1

'   Coordinates are in master units
    startPoint.X = 2.71801666666667
    startPoint.Y = 0.106315876158204
    startPoint.Z = 0#

'   Send a data point to the current command
    point.X = startPoint.X
    point.Y = startPoint.Y
    point.Z = startPoint.Z
    CadInputQueue.SendAdjustedDataPoint point, 1

'   XX-MacroComment_Header-XX

'   XX-MacroComment_InsertText-XX

'   Send a keyin that can be a command string
    CadInputQueue.SendKeyin "TEXTEDITOR PLAYCOMMAND INSERT_TEXT ""ISD-$PG$"""

    CadInputQueue.SendCommand "TEXTEDITOR PLAYCOMMAND SET_INSERT_CARET LINE 0 CHARACTER 4"

    CadInputQueue.SendKeyin "TEXTEDITOR PLAYCOMMAND INSERT_TEXT "" """

    CadInputQueue.SendCommand "TEXTEDITOR PLAYCOMMAND SET_INSERT_CARET LINE 0 CHARACTER 3"

    CadInputQueue.SendKeyin "TEXTEDITOR PLAYCOMMAND INSERT_TEXT "" """

    point.X = startPoint.X - 1.67600144444151E-02
    point.Y = startPoint.Y + 9.12509509232304E-02
    point.Z = startPoint.Z
    CadInputQueue.SendDataPoint point, 1

    CommandState.StartDefaultCommand
End Sub
Sub Wrapper_AllSheets()

    Dim oModel As ModelReference

    ' Loop through all models in the active DGN
    For Each oModel In ActiveDesignFile.Models

        ' Only run on sheet models
        If oModel.Type = msdModelTypeSheet Then

            oModel.Activate   ' make this sheet active

            ' Call the recorded macro that does the delete on this sheet
            BmrSHEET_ID_CHNG

        End If

    Next oModel

    ' Save settings after all changes
    CadInputQueue.SendCommand "FILEDESIGN SAVESETTINGS"

    MsgBox "Finished changing the title on all sheet models.", vbInformation

End Sub
