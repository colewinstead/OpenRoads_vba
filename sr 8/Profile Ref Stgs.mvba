Attribute VB_Name = "BmrProfile_Ref_StgsModalHandler"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Implements IModalDialogEvents

Private Sub IModalDialogEvents_OnDialogClosed(ByVal DialogBoxName As String, ByVal DialogResult As MsdDialogBoxResult)

End Sub

Private Sub IModalDialogEvents_OnDialogOpened(ByVal DialogBoxName As String, DialogResult As MsdDialogBoxResult)

    If Left$(DialogBoxName, Len("Attachment Properties:")) = "Attachment Properties:" Then

        SetCExpressionValue "refFileInfoP->settings.synchWithNamedViewOption", 3, "REF"
        SetCExpressionValue "refFileInfoP->sourceModelID", 0, "REF"

        DialogResult = msdDialogBoxResultOK

    End If

End Sub

Attribute VB_Name = "ModProfile_Ref_Stgs"
Option Explicit

Private Const TARGET_REFERENCE As String = "isd.dgn"

Public Sub Wrapper_AllProfiles_RefSettings()

    RunReferenceSettingsOnModels "profile", "Profile"

End Sub

Public Sub Wrapper_AllPlans_RefSettings()

    RunReferenceSettingsOnModels "plan", "Plan"

End Sub

Private Sub RunReferenceSettingsOnModels(ByVal modelNameFilter As String, ByVal label As String)

    Dim oModel As ModelReference
    Dim changedCount As Long

    For Each oModel In ActiveDesignFile.Models

        If InStr(1, oModel.Name, modelNameFilter, vbTextCompare) > 0 Then
            oModel.Activate

            ApplyReferenceSettings TARGET_REFERENCE
            changedCount = changedCount + 1
        End If

    Next oModel

    CadInputQueue.SendCommand "FILEDESIGN SAVESETTINGS"

    MsgBox "Finished updating " & label & " reference settings." & vbCrLf & vbCrLf & _
           label & " models processed: " & changedCount, _
           vbInformation, label & " Reference Settings"

End Sub

Public Sub ApplyReferenceSettings(ByVal referenceName As String)

    Dim modalHandler As New BmrProfile_Ref_StgsModalHandler

    AddModalDialogEventsHandler modalHandler

    CadInputQueue.SendCommand "REFERENCE SELECT " & referenceName
    CadInputQueue.SendCommand "REFERENCE PROPERTIES"
    CadInputQueue.SendCommand "NULL"

    RemoveModalDialogEventsHandler modalHandler

    CommandState.StartDefaultCommand

End Sub

' Keep this alias if anything still calls the old recorded macro name.
Public Sub BmrProfile_Ref_Stgs()

    ApplyReferenceSettings TARGET_REFERENCE

End Sub
