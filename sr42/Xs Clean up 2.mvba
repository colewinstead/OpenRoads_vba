Attribute VB_Name = "ModXs_Clean_up_2"
Sub BmrXs_Clean_up_2()
    Dim startPoint As Point3d
    Dim point As Point3d, point2 As Point3d
    Dim lngTemp As Long
    Dim oMessage As CadInputMessage

'   Send a keyin that can be a command string
    CadInputQueue.SendKeyin "OF=""Default"";SELVIEW 1"

    CadInputQueue.SendKeyin "OF=""XS_X_GROUND"";SELVIEW 1"

    CadInputQueue.SendKeyin "OF=""XS_SHEET_MINOR_GRIDS"";SELVIEW 1"

    CadInputQueue.SendKeyin "OF=""XS_SHEET_MEDIUM_GRIDS"";SELVIEW 1"

    CadInputQueue.SendKeyin "OF=""XS_SHEET_MAJOR_GRIDS"";SELVIEW 1"

    CadInputQueue.SendKeyin "OF=""XS_SHEET_LABELS_STATION"";SELVIEW 1"

    CadInputQueue.SendKeyin "OF=""XS_SHEET_LABELS_OFFSET"";SELVIEW 1"

    CadInputQueue.SendKeyin "OF=""XS_SHEET_LABELS_ELEVATION"";SELVIEW 1"

    CadInputQueue.SendKeyin "OF=""XS_P_TX_FS_BS"";SELVIEW 1"

    CadInputQueue.SendKeyin "OF=""SHEET_BORDER"";SELVIEW 1"

    CadInputQueue.SendKeyin "OF=""Draft_XS_Volume_Annotation"";SELVIEW 1"

    CadInputQueue.SendKeyin "OF=""Draft_Named_Boundary"";SELVIEW 1"

    CadInputQueue.SendKeyin "OF=""Draft_Civil_Labels"";SELVIEW 1"

    CadInputQueue.SendKeyin "OF=""z - Construction"";SELVIEW 1"

    CadInputQueue.SendKeyin "OF=""XS_X_UNSUITABLE_MATERIAL"";SELVIEW 1"

    CadInputQueue.SendKeyin "OF=""XS_X_UNCLASS"";SELVIEW 1"

    CadInputQueue.SendKeyin "OF=""XS_X_TX"";SELVIEW 1"

    CadInputQueue.SendKeyin "OF=""XS_X_SHOULDER"";SELVIEW 1"

    CadInputQueue.SendKeyin "OF=""XS_X_ROW"";SELVIEW 1"

    CadInputQueue.SendKeyin "OF=""XS_X_PAVEMENT"";SELVIEW 1"

    CadInputQueue.SendKeyin "OF=""XS_X_MUCK"";SELVIEW 1"

    CadInputQueue.SendKeyin "OF=""XS_X_MERGE"";SELVIEW 1"

    CadInputQueue.SendKeyin "OF=""XS_X_GROUND_TX"";SELVIEW 1"

    CadInputQueue.SendKeyin "OF=""XS_X_FINAL"";SELVIEW 1"

    CadInputQueue.SendKeyin "OF=""XS_X_EXCESS"";SELVIEW 1"

    CadInputQueue.SendKeyin "OF=""XS_X_DRAINAGE"";SELVIEW 1"

    CadInputQueue.SendKeyin "OF=""XS_X_BORROW"";SELVIEW 1"

    CadInputQueue.SendKeyin "OF=""XS_X_ADD"";SELVIEW 1"

    CadInputQueue.SendKeyin "OF=""XS_SHEET_TX"";SELVIEW 1"

    CadInputQueue.SendKeyin "OF=""XS_SHEET_LABELS_SLOPE"";SELVIEW 1"

    CadInputQueue.SendKeyin "OF=""XS_SHEET_LABELS_ALIGNMENT"";SELVIEW 1"

'   Start a command
    CadInputQueue.SendCommand "PLACE FENCE ICON"

    CadInputQueue.SendCommand "LOCK FENCE INSIDE"

'   Coordinates are in master units
    startPoint.X = -186.058644151993
    startPoint.Y = 283.600653200325
    startPoint.Z = 0#

'   Send a data point to the current command
    point.X = startPoint.X
    point.Y = startPoint.Y
    point.Z = startPoint.Z
    CadInputQueue.SendDataPoint point, 1

    point.X = startPoint.X + 324.85863970367
    point.Y = startPoint.Y - 200.107165798953
    point.Z = startPoint.Z
    CadInputQueue.SendDataPoint point, 1

    point.X = startPoint.X - 186.326870063043
    point.Y = startPoint.Y + 113.187020463529
    point.Z = startPoint.Z
    CadInputQueue.SendDataPoint point, 1

'   Send a reset to the current command
    CadInputQueue.SendReset

    point.X = startPoint.X - 189.398048067504
    point.Y = startPoint.Y + 80.1596215146027
    point.Z = startPoint.Z
    CadInputQueue.SendDataPoint point, 1

    CadInputQueue.SendCommand "PLACE FENCE ICON"

    point.X = startPoint.X - 205.168259197472
    point.Y = startPoint.Y + 95.5588382943008
    point.Z = startPoint.Z
    CadInputQueue.SendDataPoint point, 1

    point.X = startPoint.X - 205.168259197472
    point.Y = startPoint.Y + 95.5588382943006
    point.Z = startPoint.Z
    CadInputQueue.SendDataPoint point, 1

    point.X = startPoint.X - 832.336974563663
    point.Y = startPoint.Y + 439.495609861546
    point.Z = startPoint.Z
    CadInputQueue.SendDataPoint point, 1

    point.X = startPoint.X + 1136.06604173625
    point.Y = startPoint.Y - 671.684729048016
    point.Z = startPoint.Z
    CadInputQueue.SendDataPoint point, 1

    point.X = startPoint.X + 410.666081794631
    point.Y = startPoint.Y - 8.37809816832845
    point.Z = startPoint.Z
    CadInputQueue.SendDataPoint point, 1

    CadInputQueue.SendKeyin "ON=""Default"";SELVIEW 1"

    CadInputQueue.SendKeyin "ON=""XS_X_GROUND"";SELVIEW 1"

    CadInputQueue.SendKeyin "ON=""XS_SHEET_MINOR_GRIDS"";SELVIEW 1"

    CadInputQueue.SendKeyin "ON=""XS_SHEET_MEDIUM_GRIDS"";SELVIEW 1"

    CadInputQueue.SendKeyin "ON=""XS_SHEET_MAJOR_GRIDS"";SELVIEW 1"

    CadInputQueue.SendKeyin "ON=""XS_SHEET_LABELS_STATION"";SELVIEW 1"

    CadInputQueue.SendKeyin "ON=""XS_SHEET_LABELS_OFFSET"";SELVIEW 1"

    CadInputQueue.SendKeyin "ON=""XS_SHEET_LABELS_ELEVATION"";SELVIEW 1"

    CadInputQueue.SendKeyin "ON=""XS_P_TX_FS_BS"";SELVIEW 1"

    CadInputQueue.SendKeyin "ON=""SHEET_BORDER"";SELVIEW 1"

    CadInputQueue.SendKeyin "ON=""Draft_XS_Volume_Annotation"";SELVIEW 1"

    CadInputQueue.SendKeyin "ON=""Draft_Named_Boundary"";SELVIEW 1"

    CadInputQueue.SendKeyin "ON=""Draft_Civil_Labels"";SELVIEW 1"

    CadInputQueue.SendKeyin "ON=""XS_X_DRAINAGE"";SELVIEW 1"

    CadInputQueue.SendKeyin "OF=""Default"";SELVIEW 1"

    CadInputQueue.SendKeyin "OF=""XS_X_GROUND"";SELVIEW 1"

    CadInputQueue.SendKeyin "OF=""XS_SHEET_MINOR_GRIDS"";SELVIEW 1"

    CadInputQueue.SendKeyin "OF=""XS_SHEET_MEDIUM_GRIDS"";SELVIEW 1"

    CadInputQueue.SendKeyin "OF=""XS_SHEET_MAJOR_GRIDS"";SELVIEW 1"

    CadInputQueue.SendKeyin "OF=""XS_SHEET_LABELS_STATION"";SELVIEW 1"

    CadInputQueue.SendKeyin "OF=""XS_SHEET_LABELS_OFFSET"";SELVIEW 1"

    CadInputQueue.SendKeyin "OF=""XS_SHEET_LABELS_ELEVATION"";SELVIEW 1"

    CadInputQueue.SendKeyin "OF=""XS_P_TX_FS_BS"";SELVIEW 1"

    CadInputQueue.SendKeyin "ON=""XS_P_SUBGRADE_GRANULAR"";SELVIEW 1"

    CadInputQueue.SendKeyin "OF=""SHEET_BORDER"";SELVIEW 1"

    CadInputQueue.SendKeyin "OF=""Draft_XS_Volume_Annotation"";SELVIEW 1"

    CadInputQueue.SendKeyin "OF=""Draft_Named_Boundary"";SELVIEW 1"

    CadInputQueue.SendKeyin "OF=""Draft_Civil_Labels"";SELVIEW 1"

    CadInputQueue.SendKeyin "OF=""z - Construction"";SELVIEW 1"

    CadInputQueue.SendKeyin "OF=""XS_X_UNSUITABLE_MATERIAL"";SELVIEW 1"

    CadInputQueue.SendKeyin "OF=""XS_X_UNCLASS"";SELVIEW 1"

    CadInputQueue.SendKeyin "OF=""XS_X_TX"";SELVIEW 1"

    CadInputQueue.SendKeyin "OF=""XS_X_SHOULDER"";SELVIEW 1"

    CadInputQueue.SendKeyin "OF=""XS_X_ROW"";SELVIEW 1"

    CadInputQueue.SendKeyin "OF=""XS_X_PAVEMENT"";SELVIEW 1"

    CadInputQueue.SendKeyin "OF=""XS_X_MUCK"";SELVIEW 1"

    CadInputQueue.SendKeyin "OF=""XS_X_MERGE"";SELVIEW 1"

    CadInputQueue.SendKeyin "OF=""XS_X_GROUND_TX"";SELVIEW 1"

    CadInputQueue.SendKeyin "OF=""XS_X_FINAL"";SELVIEW 1"

    CadInputQueue.SendKeyin "OF=""XS_X_EXCESS"";SELVIEW 1"

    CadInputQueue.SendKeyin "OF=""XS_X_DRAINAGE"";SELVIEW 1"

    CadInputQueue.SendKeyin "OF=""XS_X_BORROW"";SELVIEW 1"

    CadInputQueue.SendKeyin "OF=""XS_X_ADD"";SELVIEW 1"

    CadInputQueue.SendKeyin "OF=""XS_SHEET_TX"";SELVIEW 1"

    CadInputQueue.SendKeyin "OF=""XS_SHEET_LABELS_SLOPE"";SELVIEW 1"

    CadInputQueue.SendKeyin "OF=""XS_SHEET_LABELS_ALIGNMENT"";SELVIEW 1"

    CadInputQueue.SendKeyin "OF=""XS_SHEET_EW_TX_VOLUME"";SELVIEW 1"

    CadInputQueue.SendKeyin "OF=""XS_SHEET_EW_TX_AREA"";SELVIEW 1"

    CadInputQueue.SendKeyin "OF=""XS_PLAN_X_OVER"";SELVIEW 1"

    CadInputQueue.SendKeyin "OF=""XS_PLAN_UNDERCUT_LIMITS"";SELVIEW 1"

    CadInputQueue.SendKeyin "OF=""XS_PLAN_PATTERN_LINES"";SELVIEW 1"

    CadInputQueue.SendKeyin "OF=""XS_PLAN_FACE_OF_ISLAND_GUTTER"";SELVIEW 1"

    CadInputQueue.SendKeyin "OF=""XS_PLAN_DITCH_LINE"";SELVIEW 1"

    CadInputQueue.SendKeyin "OF=""XS_PLAN_CLEAR_ZONE"";SELVIEW 1"

    CadInputQueue.SendKeyin "OF=""XS_PLAN_BUTT_SECTION"";SELVIEW 1"

    CadInputQueue.SendKeyin "OF=""XS_P_TX_DCH"";SELVIEW 1"

    CadInputQueue.SendKeyin "OF=""XS_P_TX_CLEARZONE"";SELVIEW 1"

    CadInputQueue.SendKeyin "OF=""XS_P_SUBGRADE_UNDERCUT"";SELVIEW 1"

    CadInputQueue.SendKeyin "OF=""XS_P_SUBGRADE_PAVEMENT"";SELVIEW 1"

    CadInputQueue.SendKeyin "OF=""XS_P_SUBGRADE_PAVED_DITCH"";SELVIEW 1"

    CadInputQueue.SendKeyin "OF=""XS_P_SUBGRADE_MILLING"";SELVIEW 1"

    CadInputQueue.SendKeyin "OF=""XS_P_SUBGRADE_MEDIAN_PAVEMENT"";SELVIEW 1"

    CadInputQueue.SendKeyin "OF=""XS_P_SUBGRADE_LEVELING"";SELVIEW 1"

    CadInputQueue.SendKeyin "OF=""XS_P_SUBGRADE_GRANULAR_C"";SELVIEW 1"

    CadInputQueue.SendKeyin "OF=""XS_P_SUBGRADE_GRANULAR_B"";SELVIEW 1"

    CadInputQueue.SendKeyin "OF=""XS_P_STRUCTURE_EXCAVATION"";SELVIEW 1"

    CadInputQueue.SendKeyin "OF=""XS_P_SIDEWALK"";SELVIEW 1"

    CadInputQueue.SendKeyin "OF=""XS_P_SHOULDER"";SELVIEW 1"

    CadInputQueue.SendKeyin "OF=""XS_P_ROW"";SELVIEW 1"

    CadInputQueue.SendKeyin "OF=""XS_P_NULL_POINT"";SELVIEW 1"

    CadInputQueue.SendKeyin "OF=""XS_P_GROUND_B"";SELVIEW 1"

    CadInputQueue.SendKeyin "OF=""XS_P_GROUND"";SELVIEW 1"

    CadInputQueue.SendKeyin "OF=""XS_P_FINISHED_GRADE_ELEV_TX"";SELVIEW 1"

    CadInputQueue.SendKeyin "OF=""XS_P_FINISHED_GRADE"";SELVIEW 1"

    CadInputQueue.SendKeyin "OF=""XS_P_DRIVEWAY"";SELVIEW 1"

    CadInputQueue.SendKeyin "OF=""XS_P_DRAINAGE"";SELVIEW 1"

    CadInputQueue.SendKeyin "OF=""XS_P_DR_GRAVEL"";SELVIEW 1"

    CadInputQueue.SendKeyin "OF=""XS_P_DR_CONCRETE"";SELVIEW 1"

    CadInputQueue.SendKeyin "OF=""XS_P_DR_ASPHALT_B"";SELVIEW 1"

    CadInputQueue.SendKeyin "OF=""XS_P_DR_ASPHALT"";SELVIEW 1"

    CadInputQueue.SendKeyin "OF=""XS_P_CURB_GUTTER"";SELVIEW 1"

    CadInputQueue.SendKeyin "OF=""XS_P_CRUSHED_STONE"";SELVIEW 1"

    CadInputQueue.SendKeyin "OF=""XS_P_CONCRETE"";SELVIEW 1"

    CadInputQueue.SendKeyin "OF=""XS_P_CHANNEL"";SELVIEW 1"

    CadInputQueue.SendKeyin "OF=""XS_P_ASPHALT"";SELVIEW 1"

    CadInputQueue.SendKeyin "OF=""XS_M_SILT_FENCE"";SELVIEW 1"

    CadInputQueue.SendKeyin "OF=""XS_M_SHAPES_EARTHWORK"";SELVIEW 1"

    CadInputQueue.SendKeyin "OF=""XS_M_MULTI"";SELVIEW 1"

    CadInputQueue.SendKeyin "OF=""XS_M_MIN_OVERLAY"";SELVIEW 1"

    CadInputQueue.SendKeyin "OF=""XS_M_FORM_GRADES"";SELVIEW 1"

    CadInputQueue.SendKeyin "OF=""XS_M_EXCAVATION_LIMITS_1"";SELVIEW 1"

    CadInputQueue.SendKeyin "OF=""XS_M_EXCAVATION_LIMITS"";SELVIEW 1"

    CadInputQueue.SendKeyin "OF=""XS_M_DITCH"";SELVIEW 1"

    CadInputQueue.SendKeyin "OF=""XS_CELL"";SELVIEW 1"

    CadInputQueue.SendKeyin "OF=""X_UTIL_WATER_VALVE"";SELVIEW 1"

    CadInputQueue.SendKeyin "OF=""X_UTIL_WATER_METER"";SELVIEW 1"

    CadInputQueue.SendKeyin "OF=""X_UTIL_WATER_LINE"";SELVIEW 1"

    CadInputQueue.SendKeyin "OF=""X_UTIL_TX"";SELVIEW 1"

    CadInputQueue.SendKeyin "OF=""X_UTIL_TRANSFORMER"";SELVIEW 1"

    CadInputQueue.SendKeyin "OF=""X_UTIL_TOWER"";SELVIEW 1"

    CadInputQueue.SendKeyin "OF=""X_UTIL_TELEPHONE_SIGN"";SELVIEW 1"

    CadInputQueue.SendKeyin "OF=""X_UTIL_TELEPHONE_POLE"";SELVIEW 1"

    CadInputQueue.SendKeyin "OF=""X_UTIL_TELEPHONE_PEDESTAL"";SELVIEW 1"

    CadInputQueue.SendKeyin "OF=""X_UTIL_TELEPHONE_LINE"";SELVIEW 1"

    CadInputQueue.SendKeyin "OF=""X_UTIL_TELEPHONE_BOOTH"";SELVIEW 1"

    CadInputQueue.SendKeyin "OF=""X_UTIL_SANITARY_SEWER_MANHOLE"";SELVIEW 1"

    CadInputQueue.SendKeyin "OF=""X_UTIL_SANITARY_SEWER"";SELVIEW 1"

    CadInputQueue.SendKeyin "OF=""X_UTIL_PULL_BOX"";SELVIEW 1"

    CadInputQueue.SendKeyin "OF=""X_UTIL_POWER_POLE"";SELVIEW 1"

    CadInputQueue.SendKeyin "OF=""X_UTIL_POWER_LINES_UNDERGROUND"";SELVIEW 1"

    CadInputQueue.SendKeyin "OF=""X_UTIL_POWER_LINES_ABOVE_GROUND"";SELVIEW 1"

    CadInputQueue.SendKeyin "OF=""X_UTIL_MISC_POLES"";SELVIEW 1"

    CadInputQueue.SendKeyin "OF=""X_UTIL_MARKER"";SELVIEW 1"

    CadInputQueue.SendKeyin "OF=""X_UTIL_MANHOLE"";SELVIEW 1"

    CadInputQueue.SendKeyin "OF=""X_UTIL_LIGHT_POLE"";SELVIEW 1"

    CadInputQueue.SendKeyin "OF=""X_UTIL_HIGH_MAST_LIGHT_POLE"";SELVIEW 1"

    CadInputQueue.SendKeyin "OF=""X_UTIL_GUY"";SELVIEW 1"

    CadInputQueue.SendKeyin "OF=""X_UTIL_GAS_VENT"";SELVIEW 1"

    CadInputQueue.SendKeyin "OF=""X_UTIL_GAS_VALVE"";SELVIEW 1"

    CadInputQueue.SendKeyin "OF=""X_UTIL_GAS_SIGN"";SELVIEW 1"

    CadInputQueue.SendKeyin "OF=""X_UTIL_GAS_METER"";SELVIEW 1"

    CadInputQueue.SendKeyin "OF=""X_UTIL_GAS_LINE"";SELVIEW 1"

    CadInputQueue.SendKeyin "OF=""X_UTIL_FIRE_HYDRANT"";SELVIEW 1"

    CadInputQueue.SendKeyin "OF=""X_UTIL_FIBER_OPTIC_CABLE"";SELVIEW 1"

    CadInputQueue.SendKeyin "OF=""X_UTIL_ESMT"";SELVIEW 1"

    CadInputQueue.SendKeyin "OF=""X_UTIL_ELECTRIC_METER"";SELVIEW 1"

    CadInputQueue.SendKeyin "OF=""X_UTIL_CABLE_POLE"";SELVIEW 1"

    CadInputQueue.SendKeyin "OF=""X_UTIL_CABLE_LINE"";SELVIEW 1"

    CadInputQueue.SendKeyin "OF=""X_UTIL_CABLE_BOX"";SELVIEW 1"

    CadInputQueue.SendKeyin "OF=""X_UTIL_ANTENNAS"";SELVIEW 1"

    CadInputQueue.SendKeyin "OF=""X_TRANS_TX"";SELVIEW 1"

    CadInputQueue.SendKeyin "OF=""X_TRANS_SIDEWALK"";SELVIEW 1"

    CadInputQueue.SendKeyin "OF=""X_TRANS_SHLDRS_UNPAVED"";SELVIEW 1"

    CadInputQueue.SendKeyin "OF=""X_TRANS_SHLDRS_PAVED"";SELVIEW 1"

    CadInputQueue.SendKeyin "OF=""X_TRANS_RET_WALLS"";SELVIEW 1"

    CadInputQueue.SendKeyin "OF=""X_TRANS_RAILROAD_DEVICES"";SELVIEW 1"

    CadInputQueue.SendKeyin "OF=""X_TRANS_RAILROAD"";SELVIEW 1"

    CadInputQueue.SendKeyin "OF=""X_TRANS_PARKING_LOTS"";SELVIEW 1"

    CadInputQueue.SendKeyin "OF=""X_TRANS_EOP"";SELVIEW 1"

    CadInputQueue.SendKeyin "OF=""X_TRANS_EOG"";SELVIEW 1"

    CadInputQueue.SendKeyin "OF=""X_TRANS_DRIVES"";SELVIEW 1"

    CadInputQueue.SendKeyin "OF=""X_TRANS_CURB_GUTTER"";SELVIEW 1"

    CadInputQueue.SendKeyin "OF=""X_TRANS_BRIDGES"";SELVIEW 1"

    CadInputQueue.SendKeyin "OF=""X_TRANS_BRIDGE_COLUMN"";SELVIEW 1"

    CadInputQueue.SendKeyin "OF=""X_SIGNAL_TX"";SELVIEW 1"

    CadInputQueue.SendKeyin "OF=""X_SIGNAL_POLE"";SELVIEW 1"

    CadInputQueue.SendKeyin "OF=""X_SIGNAL_HEADS"";SELVIEW 1"

    CadInputQueue.SendKeyin "OF=""X_SIGNAL_CONTROL_BOX"";SELVIEW 1"

    CadInputQueue.SendKeyin "OF=""X_SIGN_TX"";SELVIEW 1"

    CadInputQueue.SendKeyin "OF=""X_SIGN_POST"";SELVIEW 1"

    CadInputQueue.SendKeyin "OF=""X_SIGN_OVERHEAD"";SELVIEW 1"

    CadInputQueue.SendKeyin "OF=""X_SIGN_HISTORICAL_MARKER"";SELVIEW 1"

    CadInputQueue.SendKeyin "OF=""X_SIGN_BILLBOARD"";SELVIEW 1"

    CadInputQueue.SendKeyin "OF=""X_SAFETY_DEV_TX"";SELVIEW 1"

    CadInputQueue.SendKeyin "OF=""X_SAFETY_DEV_GUARDRAIL_RT"";SELVIEW 1"

    CadInputQueue.SendKeyin "OF=""X_SAFETY_DEV_GUARDRAIL_LT"";SELVIEW 1"

    CadInputQueue.SendKeyin "OF=""X_SAFETY_DEV_CABLE_BARRIERS"";SELVIEW 1"

    CadInputQueue.SendKeyin "OF=""X_SAFETY_DEV_BARRIERS"";SELVIEW 1"

    CadInputQueue.SendKeyin "OF=""X_SAFETY_DEV_ATTENUATORS"";SELVIEW 1"

    CadInputQueue.SendKeyin "OF=""X_ROW_TX"";SELVIEW 1"

    CadInputQueue.SendKeyin "OF=""X_ROW_NO_ACCESS_LIMITS"";SELVIEW 1"

    CadInputQueue.SendKeyin "OF=""X_ROW_MARKERS_COMPUTED"";SELVIEW 1"

    CadInputQueue.SendKeyin "OF=""X_ROW_MARKERS"";SELVIEW 1"

    CadInputQueue.SendKeyin "OF=""X_ROW_EASEMENTS"";SELVIEW 1"

    CadInputQueue.SendKeyin "OF=""X_ROW"";SELVIEW 1"

    CadInputQueue.SendKeyin "OF=""X_PROPERTY_URBAN_LIMITS"";SELVIEW 1"

    CadInputQueue.SendKeyin "OF=""X_PROPERTY_TX"";SELVIEW 1"

    CadInputQueue.SendKeyin "OF=""X_PROPERTY_TOWNSHIP_LINES"";SELVIEW 1"

    CadInputQueue.SendKeyin "OF=""X_PROPERTY_STATE_BORDER"";SELVIEW 1"

    CadInputQueue.SendKeyin "OF=""X_PROPERTY_SET_IRON_PIN"";SELVIEW 1"

    CadInputQueue.SendKeyin "OF=""X_PROPERTY_SECTION_LINES_W_FENCE"";SELVIEW 1"

    CadInputQueue.SendKeyin "OF=""X_PROPERTY_SECTION_LINES"";SELVIEW 1"

    CadInputQueue.SendKeyin "OF=""X_PROPERTY_QUARTER_LINES"";SELVIEW 1"

    CadInputQueue.SendKeyin "OF=""X_PROPERTY_PAINTED_LINES"";SELVIEW 1"

    CadInputQueue.SendKeyin "OF=""X_PROPERTY_OWNERS_TX"";SELVIEW 1"

    CadInputQueue.SendKeyin "OF=""X_PROPERTY_NAILS"";SELVIEW 1"

    CadInputQueue.SendKeyin "OF=""X_PROPERTY_LOT_LINES"";SELVIEW 1"

    CadInputQueue.SendKeyin "OF=""X_PROPERTY_LINES_W_FENCE"";SELVIEW 1"

    CadInputQueue.SendKeyin "OF=""X_PROPERTY_LINES"";SELVIEW 1"

    CadInputQueue.SendKeyin "OF=""X_PROPERTY_LAND_HOOK"";SELVIEW 1"

    CadInputQueue.SendKeyin "OF=""X_PROPERTY_FOUND_SECTION_CORNER"";SELVIEW 1"

    CadInputQueue.SendKeyin "OF=""X_PROPERTY_FOUND_IRON_PIN"";SELVIEW 1"

    CadInputQueue.SendKeyin "OF=""X_PROPERTY_FOUND_CORNER"";SELVIEW 1"

    CadInputQueue.SendKeyin "OF=""X_PROPERTY_DEED_LINES"";SELVIEW 1"

    CadInputQueue.SendKeyin "OF=""X_PROPERTY_COUNTY_LINES"";SELVIEW 1"

    CadInputQueue.SendKeyin "OF=""X_PROPERTY_40_LINES"";SELVIEW 1"

    CadInputQueue.SendKeyin "OF=""X_PROFILES_DCH_TX"";SELVIEW 1"

    CadInputQueue.SendKeyin "OF=""X_PROFILES_DCH_2"";SELVIEW 1"

    CadInputQueue.SendKeyin "OF=""X_PROFILES_DCH_1"";SELVIEW 1"

    CadInputQueue.SendKeyin "OF=""X_PROFILES_2"";SELVIEW 1"

    CadInputQueue.SendKeyin "OF=""X_PROFILES_1"";SELVIEW 1"

    CadInputQueue.SendKeyin "OF=""X_PROFILE_TX_STRIP"";SELVIEW 1"

    CadInputQueue.SendKeyin "OF=""X_PROFILE_TX"";SELVIEW 1"

    CadInputQueue.SendKeyin "OF=""X_PROFILE_SEWER"";SELVIEW 1"

    CadInputQueue.SendKeyin "OF=""X_PROFILE_DRAINAGE_TX"";SELVIEW 1"

    CadInputQueue.SendKeyin "OF=""X_PROFILE_DRAINAGE"";SELVIEW 1"

    CadInputQueue.SendKeyin "OF=""X_POINT_TRAV"";SELVIEW 1"

    CadInputQueue.SendKeyin "OF=""X_POINT_TOB_LINES"";SELVIEW 1"

    CadInputQueue.SendKeyin "OF=""X_POINT_SPOT"";SELVIEW 1"

    CadInputQueue.SendKeyin "OF=""X_POINT_PHOTO"";SELVIEW 1"

    CadInputQueue.SendKeyin "OF=""X_POINT_NUMBER_TX"";SELVIEW 1"

    CadInputQueue.SendKeyin "OF=""X_POINT_LIDAR_HARD_SURFACES"";SELVIEW 1"

    CadInputQueue.SendKeyin "OF=""X_POINT_LIDAR"";SELVIEW 1"

    CadInputQueue.SendKeyin "OF=""X_POINT_ELEVATION_TX"";SELVIEW 1"

    CadInputQueue.SendKeyin "OF=""X_POINT_DESCRIPTION_TX"";SELVIEW 1"

    CadInputQueue.SendKeyin "OF=""X_POINT_COORDINATE_TX"";SELVIEW 1"

    CadInputQueue.SendKeyin "OF=""X_POINT_COORDINATE_GRIDS"";SELVIEW 1"

    CadInputQueue.SendKeyin "OF=""X_POINT_CHECK"";SELVIEW 1"

    CadInputQueue.SendKeyin "OF=""X_POINT_BREAK_LINES"";SELVIEW 1"

    CadInputQueue.SendKeyin "OF=""X_POINT"";SELVIEW 1"

    CadInputQueue.SendKeyin "OF=""X_PM_STRIPE_TX"";SELVIEW 1"

    CadInputQueue.SendKeyin "OF=""X_PM_STRIPE"";SELVIEW 1"

    CadInputQueue.SendKeyin "OF=""X_PM_RAISED_MARKERS_TX"";SELVIEW 1"

    CadInputQueue.SendKeyin "OF=""X_PM_RAISED_MARKERS"";SELVIEW 1"

    CadInputQueue.SendKeyin "OF=""X_NON_TRANS_WELLS"";SELVIEW 1"

    CadInputQueue.SendKeyin "OF=""X_NON_TRANS_WATER_TOWER"";SELVIEW 1"

    CadInputQueue.SendKeyin "OF=""X_NON_TRANS_WALKWAY"";SELVIEW 1"

    CadInputQueue.SendKeyin "OF=""X_NON_TRANS_VACUUM"";SELVIEW 1"

    CadInputQueue.SendKeyin "OF=""X_NON_TRANS_TX"";SELVIEW 1"

    CadInputQueue.SendKeyin "OF=""X_NON_TRANS_TREES_LINES"";SELVIEW 1"

    CadInputQueue.SendKeyin "OF=""X_NON_TRANS_TREES"";SELVIEW 1"

    CadInputQueue.SendKeyin "OF=""X_NON_TRANS_TOWERS"";SELVIEW 1"

    CadInputQueue.SendKeyin "OF=""X_NON_TRANS_TANKS_UNDERGROUND"";SELVIEW 1"

    CadInputQueue.SendKeyin "OF=""X_NON_TRANS_TANKS_PROPANE"";SELVIEW 1"

    CadInputQueue.SendKeyin "OF=""X_NON_TRANS_TANKS_ABOVE_GROUND"";SELVIEW 1"

    CadInputQueue.SendKeyin "OF=""X_NON_TRANS_SPRINKLER"";SELVIEW 1"

    CadInputQueue.SendKeyin "OF=""X_NON_TRANS_SEA_WALL"";SELVIEW 1"

    CadInputQueue.SendKeyin "OF=""X_NON_TRANS_SATELLITE_DISH"";SELVIEW 1"

    CadInputQueue.SendKeyin "OF=""X_NON_TRANS_RET_WALLS"";SELVIEW 1"

    CadInputQueue.SendKeyin "OF=""X_NON_TRANS_POOL"";SELVIEW 1"

    CadInputQueue.SendKeyin "OF=""X_NON_TRANS_PITS"";SELVIEW 1"

    CadInputQueue.SendKeyin "OF=""X_NON_TRANS_PARKING_METER"";SELVIEW 1"

    CadInputQueue.SendKeyin "OF=""X_NON_TRANS_PARKING_LOTS"";SELVIEW 1"

    CadInputQueue.SendKeyin "OF=""X_NON_TRANS_MAILBOXS"";SELVIEW 1"

    CadInputQueue.SendKeyin "OF=""X_NON_TRANS_HOSPITALS"";SELVIEW 1"

    CadInputQueue.SendKeyin "OF=""X_NON_TRANS_HEDGE_ROW"";SELVIEW 1"

    CadInputQueue.SendKeyin "OF=""X_NON_TRANS_GRAVE_SITE"";SELVIEW 1"

    CadInputQueue.SendKeyin "OF=""X_NON_TRANS_GAS_PUMP"";SELVIEW 1"

    CadInputQueue.SendKeyin "OF=""X_NON_TRANS_FLAG_POLES"";SELVIEW 1"

    CadInputQueue.SendKeyin "OF=""X_NON_TRANS_FENCES"";SELVIEW 1"

    CadInputQueue.SendKeyin "OF=""X_NON_TRANS_CONCRETE_PAD"";SELVIEW 1"

    CadInputQueue.SendKeyin "OF=""X_NON_TRANS_CEMETERIES"";SELVIEW 1"

    CadInputQueue.SendKeyin "OF=""X_NON_TRANS_CATTLE_GAP"";SELVIEW 1"

    CadInputQueue.SendKeyin "OF=""X_NON_TRANS_BUILDINGS"";SELVIEW 1"

    CadInputQueue.SendKeyin "OF=""X_NON_TRANS_AIRPORT_RUNWAYS"";SELVIEW 1"

    CadInputQueue.SendKeyin "OF=""X_DRAINAGE_WETLANDS"";SELVIEW 1"

    CadInputQueue.SendKeyin "OF=""X_DRAINAGE_UNDERDRAINS"";SELVIEW 1"

    CadInputQueue.SendKeyin "OF=""X_DRAINAGE_TX"";SELVIEW 1"

    CadInputQueue.SendKeyin "OF=""X_DRAINAGE_STREAMS_RIVERS"";SELVIEW 1"

    CadInputQueue.SendKeyin "OF=""X_DRAINAGE_SPUR_DIKES"";SELVIEW 1"

    CadInputQueue.SendKeyin "OF=""X_DRAINAGE_RIP_RAP"";SELVIEW 1"

    CadInputQueue.SendKeyin "OF=""X_DRAINAGE_PONDS_AND_LAKES"";SELVIEW 1"

    CadInputQueue.SendKeyin "OF=""X_DRAINAGE_PIPES"";SELVIEW 1"

    CadInputQueue.SendKeyin "OF=""X_DRAINAGE_MANHOLES"";SELVIEW 1"

    CadInputQueue.SendKeyin "OF=""X_DRAINAGE_INLETS"";SELVIEW 1"

    CadInputQueue.SendKeyin "OF=""X_DRAINAGE_FLUMES"";SELVIEW 1"

    CadInputQueue.SendKeyin "OF=""X_DRAINAGE_FLARED_END_SECTION"";SELVIEW 1"

    CadInputQueue.SendKeyin "OF=""X_DRAINAGE_END_WALLS"";SELVIEW 1"

    CadInputQueue.SendKeyin "OF=""X_DRAINAGE_DITCHES"";SELVIEW 1"

    CadInputQueue.SendKeyin "OF=""X_DRAINAGE_DITCH_PLUGS"";SELVIEW 1"

    CadInputQueue.SendKeyin "OF=""X_DRAINAGE_DAMS"";SELVIEW 1"

    CadInputQueue.SendKeyin "OF=""X_DRAINAGE_BOX_CULV"";SELVIEW 1"

    CadInputQueue.SendKeyin "OF=""X_DRAINAGE_AREA"";SELVIEW 1"

    CadInputQueue.SendKeyin "OF=""X_DRAINAGE_APRONS"";SELVIEW 1"

    CadInputQueue.SendKeyin "OF=""X_ALI_TEMP_BENCHMARK_CTRL"";SELVIEW 1"

    CadInputQueue.SendKeyin "OF=""X_ALI_SURVEY_SECONDARY_TICS_SMALL"";SELVIEW 1"

    CadInputQueue.SendKeyin "OF=""X_ALI_SURVEY_SECONDARY_TICS"";SELVIEW 1"

    CadInputQueue.SendKeyin "OF=""X_ALI_SURVEY_SECONDARY_STA_SMALL"";SELVIEW 1"

    CadInputQueue.SendKeyin "OF=""X_ALI_SURVEY_SECONDARY_STA"";SELVIEW 1"

    CadInputQueue.SendKeyin "OF=""X_ALI_SURVEY_SECONDARY_LABELS_TX"";SELVIEW 1"

    CadInputQueue.SendKeyin "OF=""X_ALI_SURVEY_SECONDARY_LABELS"";SELVIEW 1"

    CadInputQueue.SendKeyin "OF=""X_ALI_SURVEY_SECONDARY_CURVES"";SELVIEW 1"

    CadInputQueue.SendKeyin "OF=""X_ALI_SURVEY_SECONDARY_CURVE_DATA"";SELVIEW 1"

    CadInputQueue.SendKeyin "OF=""X_ALI_SURVEY_SECONDARY"";SELVIEW 1"

    CadInputQueue.SendKeyin "OF=""X_ALI_SURVEY_ML_TICS_SMALL"";SELVIEW 1"

    CadInputQueue.SendKeyin "OF=""X_ALI_SURVEY_ML_TICS"";SELVIEW 1"

    CadInputQueue.SendKeyin "OF=""X_ALI_SURVEY_ML_STA_SMALL"";SELVIEW 1"

    CadInputQueue.SendKeyin "OF=""X_ALI_SURVEY_ML_STA"";SELVIEW 1"

    CadInputQueue.SendKeyin "OF=""X_ALI_SURVEY_ML_LABELS_TX"";SELVIEW 1"

    CadInputQueue.SendKeyin "OF=""X_ALI_SURVEY_ML_LABELS"";SELVIEW 1"

    CadInputQueue.SendKeyin "OF=""X_ALI_SURVEY_ML_CURVES"";SELVIEW 1"

    CadInputQueue.SendKeyin "OF=""X_ALI_SURVEY_ML_CURVE_DATA"";SELVIEW 1"

    CadInputQueue.SendKeyin "OF=""X_ALI_SURVEY_ML"";SELVIEW 1"

    CadInputQueue.SendKeyin "OF=""X_ALI_SURVEY_LR_TICS_SMALL"";SELVIEW 1"

    CadInputQueue.SendKeyin "OF=""X_ALI_SURVEY_LR_TICS"";SELVIEW 1"

    CadInputQueue.SendKeyin "OF=""X_ALI_SURVEY_LR_STA_SMALL"";SELVIEW 1"

    CadInputQueue.SendKeyin "OF=""X_ALI_SURVEY_LR_STA"";SELVIEW 1"

    CadInputQueue.SendKeyin "OF=""X_ALI_SURVEY_LR_LABELS_TX"";SELVIEW 1"

    CadInputQueue.SendKeyin "OF=""X_ALI_SURVEY_LR_LABELS"";SELVIEW 1"

    CadInputQueue.SendKeyin "OF=""X_ALI_SURVEY_LR_CURVES"";SELVIEW 1"

    CadInputQueue.SendKeyin "OF=""X_ALI_SURVEY_LR_CURVE_DATA"";SELVIEW 1"

    CadInputQueue.SendKeyin "OF=""X_ALI_SURVEY_LR"";SELVIEW 1"

    CadInputQueue.SendKeyin "OF=""X_ALI_SURVEY_GPS_DATA"";SELVIEW 1"

    CadInputQueue.SendKeyin "OF=""X_ALI_SURVEY_DRAINAGE_TICS_SMALL"";SELVIEW 1"

    CadInputQueue.SendKeyin "OF=""X_ALI_SURVEY_DRAINAGE_TICS"";SELVIEW 1"

    CadInputQueue.SendKeyin "OF=""X_ALI_SURVEY_DRAINAGE_STA_SMALL"";SELVIEW 1"

    CadInputQueue.SendKeyin "OF=""X_ALI_SURVEY_DRAINAGE_STA"";SELVIEW 1"

    CadInputQueue.SendKeyin "OF=""X_ALI_SURVEY_DRAINAGE_LABELS_TX"";SELVIEW 1"

    CadInputQueue.SendKeyin "OF=""X_ALI_SURVEY_DRAINAGE_LABELS"";SELVIEW 1"

    CadInputQueue.SendKeyin "OF=""X_ALI_SURVEY_DRAINAGE_CURVE_DATA"";SELVIEW 1"

    CadInputQueue.SendKeyin "OF=""X_ALI_SURVEY_DRAINAGE"";SELVIEW 1"

    CadInputQueue.SendKeyin "OF=""X_Ali_Survey_Baseline_Sta"";SELVIEW 1"

    CadInputQueue.SendKeyin "OF=""X_Ali_Survey_Baseline_Curve_Data"";SELVIEW 1"

    CadInputQueue.SendKeyin "OF=""X_Ali_Survey_Baseline"";SELVIEW 1"

    CadInputQueue.SendKeyin "OF=""X_ALI_SURVEY_AUX_TICS_SMALL"";SELVIEW 1"

    CadInputQueue.SendKeyin "OF=""X_ALI_SURVEY_AUX_TICS"";SELVIEW 1"

    CadInputQueue.SendKeyin "OF=""X_ALI_SURVEY_AUX_STA_SMALL"";SELVIEW 1"

    CadInputQueue.SendKeyin "OF=""X_ALI_SURVEY_AUX_STA"";SELVIEW 1"

    CadInputQueue.SendKeyin "OF=""X_ALI_SURVEY_AUX_LABELS_TX"";SELVIEW 1"

    CadInputQueue.SendKeyin "OF=""X_ALI_SURVEY_AUX_LABELS"";SELVIEW 1"

    CadInputQueue.SendKeyin "OF=""X_ALI_SURVEY_AUX_CURVES"";SELVIEW 1"

    CadInputQueue.SendKeyin "OF=""X_ALI_SURVEY_AUX_CURVE_DATA"";SELVIEW 1"

    CadInputQueue.SendKeyin "OF=""X_ALI_SURVEY_AUX"";SELVIEW 1"

    CadInputQueue.SendKeyin "OF=""X_ALI_SECONDARY_CTRL"";SELVIEW 1"

    CadInputQueue.SendKeyin "OF=""X_ALI_PRIMARY_CTRL"";SELVIEW 1"

    CadInputQueue.SendKeyin "OF=""X_ALI_NGS_CTRL"";SELVIEW 1"

    CadInputQueue.SendKeyin "OF=""X_ALI_HORIZ_AND_VERT_CTRL"";SELVIEW 1"

    CadInputQueue.SendKeyin "OF=""X_ALI_EX_CL_TICS"";SELVIEW 1"

    CadInputQueue.SendKeyin "OF=""X_ALI_EX_CL_STA"";SELVIEW 1"

    CadInputQueue.SendKeyin "OF=""X_ALI_EX_CL_LABELS"";SELVIEW 1"

    CadInputQueue.SendKeyin "OF=""X_ALI_EX_CL_CURVE_DATA"";SELVIEW 1"

    CadInputQueue.SendKeyin "OF=""X_ALI_EX_CL"";SELVIEW 1"

    CadInputQueue.SendKeyin "OF=""X_ALI_BENCHMARK_CTRL"";SELVIEW 1"

    CadInputQueue.SendKeyin "OF=""WORKING_LV10"";SELVIEW 1"

    CadInputQueue.SendKeyin "OF=""WORKING_LV9"";SELVIEW 1"

    CadInputQueue.SendKeyin "OF=""WORKING_LV8"";SELVIEW 1"

    CadInputQueue.SendKeyin "OF=""WORKING_LV7"";SELVIEW 1"

    CadInputQueue.SendKeyin "OF=""WORKING_LV6"";SELVIEW 1"

    CadInputQueue.SendKeyin "OF=""WORKING_LV5"";SELVIEW 1"

    CadInputQueue.SendKeyin "OF=""WORKING_LV4"";SELVIEW 1"

    CadInputQueue.SendKeyin "OF=""WORKING_LV3"";SELVIEW 1"

    CadInputQueue.SendKeyin "OF=""WORKING_LV2"";SELVIEW 1"

    CadInputQueue.SendKeyin "OF=""WORKING_LV1"";SELVIEW 1"

    CadInputQueue.SendKeyin "OF=""Volumes_Fill"";SELVIEW 1"

    CadInputQueue.SendKeyin "OF=""Volumes_Cut"";SELVIEW 1"

    CadInputQueue.SendKeyin "OF=""TS_X_NOTES"";SELVIEW 1"

    CadInputQueue.SendKeyin "OF=""TS_X_GROUND"";SELVIEW 1"

    CadInputQueue.SendKeyin "OF=""TS_UNDERDRAINS"";SELVIEW 1"

    CadInputQueue.SendKeyin "OF=""TS_TITLE_BLOCK_TX"";SELVIEW 1"

    CadInputQueue.SendKeyin "OF=""TS_SUBGRADE"";SELVIEW 1"

    CadInputQueue.SendKeyin "OF=""TS_SPECIAL_NOTES"";SELVIEW 1"

    CadInputQueue.SendKeyin "OF=""TS_SLOPES_TX"";SELVIEW 1"

    CadInputQueue.SendKeyin "OF=""TS_SIDEWALK"";SELVIEW 1"

    CadInputQueue.SendKeyin "OF=""TS_SIDE_SLOPE_RT"";SELVIEW 1"

    CadInputQueue.SendKeyin "OF=""TS_SIDE_SLOPE_LT"";SELVIEW 1"

    CadInputQueue.SendKeyin "OF=""TS_RETAINING_WALL"";SELVIEW 1"

    CadInputQueue.SendKeyin "OF=""TS_PROPOSED_NOTES"";SELVIEW 1"

    CadInputQueue.SendKeyin "OF=""TS_PROPOSED_LABELS"";SELVIEW 1"

    CadInputQueue.SendKeyin "OF=""TS_PAVMT_DETERMINATION"";SELVIEW 1"

    CadInputQueue.SendKeyin "OF=""TS_MATCH_LINES"";SELVIEW 1"

    CadInputQueue.SendKeyin "OF=""TS_GUARDRAIL"";SELVIEW 1"

    CadInputQueue.SendKeyin "OF=""TS_GRASS"";SELVIEW 1"

    CadInputQueue.SendKeyin "OF=""TS_FILL_SLOPE_SCHEDULE"";SELVIEW 1"

    CadInputQueue.SendKeyin "OF=""TS_EXISTING_LABELS"";SELVIEW 1"

    CadInputQueue.SendKeyin "OF=""TS_DRAINAGE"";SELVIEW 1"

    CadInputQueue.SendKeyin "OF=""TS_DIRECTION"";SELVIEW 1"

    CadInputQueue.SendKeyin "OF=""TS_DIMENSIONS_TX"";SELVIEW 1"

    CadInputQueue.SendKeyin "OF=""TS_DIMENSIONS"";SELVIEW 1"

    CadInputQueue.SendKeyin "OF=""TS_DETAILS"";SELVIEW 1"

    CadInputQueue.SendKeyin "OF=""TS_DESCRIPTIONS_TX"";SELVIEW 1"

    CadInputQueue.SendKeyin "OF=""TS_CURB_GUTTER"";SELVIEW 1"

    CadInputQueue.SendKeyin "OF=""TS_BARRIERS"";SELVIEW 1"

    CadInputQueue.SendKeyin "OF=""TS_BACKBONE"";SELVIEW 1"

    CadInputQueue.SendKeyin "OF=""TS_AREA_PATTERNS"";SELVIEW 1"

    CadInputQueue.SendKeyin "OF=""TS_ANGLE_REPOSE"";SELVIEW 1"

    CadInputQueue.SendKeyin "OF=""TRANS_UNPAVED_SHOULDERS"";SELVIEW 1"

    CadInputQueue.SendKeyin "OF=""TRANS_TX"";SELVIEW 1"

    CadInputQueue.SendKeyin "OF=""TRANS_SIDEWALK"";SELVIEW 1"

    CadInputQueue.SendKeyin "OF=""TRANS_RET_WALL"";SELVIEW 1"

    CadInputQueue.SendKeyin "OF=""TRANS_PAVED_SHOULDERS"";SELVIEW 1"

    CadInputQueue.SendKeyin "OF=""TRANS_LANE_LINE"";SELVIEW 1"

    CadInputQueue.SendKeyin "OF=""TRANS_EOP_WIDENING"";SELVIEW 1"

    CadInputQueue.SendKeyin "OF=""TRANS_EOP_UNPAVED"";SELVIEW 1"

    CadInputQueue.SendKeyin "OF=""TRANS_EOP_PAVED"";SELVIEW 1"

    CadInputQueue.SendKeyin "OF=""TRANS_EOP_INT"";SELVIEW 1"

    CadInputQueue.SendKeyin "OF=""TRANS_DRIVES"";SELVIEW 1"

    CadInputQueue.SendKeyin "OF=""TRANS_CURB_GUTTER"";SELVIEW 1"

    CadInputQueue.SendKeyin "OF=""TRANS_CL_ASPHALT"";SELVIEW 1"

    CadInputQueue.SendKeyin "OF=""TRANS_BRIDGE"";SELVIEW 1"

    CadInputQueue.SendKeyin "OF=""TRANS_BOX_BRIDGE"";SELVIEW 1"

    CadInputQueue.SendKeyin "OF=""TI_X_RAILROAD_ABD"";SELVIEW 1"

    CadInputQueue.SendKeyin "OF=""TI_X_RAILROAD"";SELVIEW 1"

    CadInputQueue.SendKeyin "OF=""TI_X_PROPERTY_URBAN_A"";SELVIEW 1"

    CadInputQueue.SendKeyin "OF=""TI_X_PROPERTY_STATE_PARK"";SELVIEW 1"

    CadInputQueue.SendKeyin "OF=""TI_X_PROPERTY_SECTION_L"";SELVIEW 1"

    CadInputQueue.SendKeyin "OF=""TI_X_PROPERTY_NAT_PARK"";SELVIEW 1"

    CadInputQueue.SendKeyin "OF=""TI_X_PROPERTY_NAT_FOREST"";SELVIEW 1"

    CadInputQueue.SendKeyin "OF=""TI_X_PROPERTY_COUNTY"";SELVIEW 1"

    CadInputQueue.SendKeyin "OF=""TI_X_PROPERTY_CITY"";SELVIEW 1"

    CadInputQueue.SendKeyin "OF=""TI_X_MISC"";SELVIEW 1"

    CadInputQueue.SendKeyin "OF=""TI_X_DRAINAGE_STREAM"";SELVIEW 1"

    CadInputQueue.SendKeyin "OF=""TI_X_DRAINAGE_RIVER"";SELVIEW 1"

    CadInputQueue.SendKeyin "OF=""TI_X_DRAINAGE_LAKE"";SELVIEW 1"

    CadInputQueue.SendKeyin "OF=""TI_X_DRAINAGE_GULF"";SELVIEW 1"

    CadInputQueue.SendKeyin "OF=""TI_X_DRAINAGE_CULV"";SELVIEW 1"

    CadInputQueue.SendKeyin "OF=""TI_X_CHURCH"";SELVIEW 1"

    CadInputQueue.SendKeyin "OF=""TI_X_CEMETERIES"";SELVIEW 1"

    CadInputQueue.SendKeyin "OF=""TI_X_BRIDGES_O"";SELVIEW 1"

    CadInputQueue.SendKeyin "OF=""TI_X_BRIDGES"";SELVIEW 1"

    CadInputQueue.SendKeyin "OF=""TI_X_ALI_US"";SELVIEW 1"

    CadInputQueue.SendKeyin "OF=""TI_X_ALI_MS"";SELVIEW 1"

    CadInputQueue.SendKeyin "OF=""TI_X_ALI_LR"";SELVIEW 1"

    CadInputQueue.SendKeyin "OF=""TI_X_ALI_INT"";SELVIEW 1"

    CadInputQueue.SendKeyin "OF=""TI_X_ALI"";SELVIEW 1"

    CadInputQueue.SendKeyin "OF=""TI_X_AIRPORT"";SELVIEW 1"

    CadInputQueue.SendKeyin "OF=""Terrain_Void"";SELVIEW 1"

    CadInputQueue.SendKeyin "OF=""Terrain_Triangle_Vertices"";SELVIEW 1"

    CadInputQueue.SendKeyin "OF=""Terrain_Triangle"";SELVIEW 1"

    CadInputQueue.SendKeyin "OF=""Terrain_Points_Random"";SELVIEW 1"

    CadInputQueue.SendKeyin "OF=""Terrain_Points_Low"";SELVIEW 1"

    CadInputQueue.SendKeyin "OF=""Terrain_Points_Inferred"";SELVIEW 1"

    CadInputQueue.SendKeyin "OF=""Terrain_Points_High"";SELVIEW 1"

    CadInputQueue.SendKeyin "OF=""Terrain_Island"";SELVIEW 1"

    CadInputQueue.SendKeyin "OF=""Terrain_Interior"";SELVIEW 1"

    CadInputQueue.SendKeyin "OF=""Terrain_Hole"";SELVIEW 1"

    CadInputQueue.SendKeyin "OF=""Terrain_Flow_Arrows"";SELVIEW 1"

    CadInputQueue.SendKeyin "OF=""Terrain_Exterior"";SELVIEW 1"

    CadInputQueue.SendKeyin "OF=""Terrain_Design"";SELVIEW 1"

    CadInputQueue.SendKeyin "OF=""Terrain_Contour_Minor"";SELVIEW 1"

    CadInputQueue.SendKeyin "OF=""Terrain_Contour_Major"";SELVIEW 1"

    CadInputQueue.SendKeyin "OF=""Terrain_Contour_Imported"";SELVIEW 1"

    CadInputQueue.SendKeyin "OF=""Terrain_Breakline"";SELVIEW 1"

    CadInputQueue.SendKeyin "OF=""TCP_UNPAVED_SHLDRS"";SELVIEW 1"

    CadInputQueue.SendKeyin "OF=""TCP_TX"";SELVIEW 1"

    CadInputQueue.SendKeyin "OF=""TCP_SIGNS_OP"";SELVIEW 1"

    CadInputQueue.SendKeyin "OF=""TCP_SIGNS_CONST"";SELVIEW 1"

    CadInputQueue.SendKeyin "OF=""TCP_SIGNALS_OP"";SELVIEW 1"

    CadInputQueue.SendKeyin "OF=""TCP_SIGNALS_CONST"";SELVIEW 1"

    CadInputQueue.SendKeyin "OF=""TCP_SIDEWALKS"";SELVIEW 1"

    CadInputQueue.SendKeyin "OF=""TCP_PM_TEMP_STRIPE"";SELVIEW 1"

    CadInputQueue.SendKeyin "OF=""TCP_PM_TEMP_MARKING_TX"";SELVIEW 1"

    CadInputQueue.SendKeyin "OF=""TCP_PAVED_SHLDRS"";SELVIEW 1"

    CadInputQueue.SendKeyin "OF=""TCP_OPERATION_TX"";SELVIEW 1"

    CadInputQueue.SendKeyin "OF=""TCP_FLASHING_PANELS_OP"";SELVIEW 1"

    CadInputQueue.SendKeyin "OF=""TCP_FLASHING_PANELS_CONST"";SELVIEW 1"

    CadInputQueue.SendKeyin "OF=""TCP_EOP"";SELVIEW 1"

    CadInputQueue.SendKeyin "OF=""TCP_DRUMS_OP"";SELVIEW 1"

    CadInputQueue.SendKeyin "OF=""TCP_DRUMS_CONST"";SELVIEW 1"

    CadInputQueue.SendKeyin "OF=""TCP_DRIVES"";SELVIEW 1"

    CadInputQueue.SendKeyin "OF=""TCP_CURB_GUTTER"";SELVIEW 1"

    CadInputQueue.SendKeyin "OF=""TCP_CONSTRUCTION_TX"";SELVIEW 1"

    CadInputQueue.SendKeyin "OF=""TCP_BRIDGES"";SELVIEW 1"

    CadInputQueue.SendKeyin "OF=""TCP_BARRIERS_OP"";SELVIEW 1"

    CadInputQueue.SendKeyin "OF=""TCP_BARRIERS_CONST"";SELVIEW 1"

    CadInputQueue.SendKeyin "OF=""TCP_BARRICADES_OP"";SELVIEW 1"

    CadInputQueue.SendKeyin "OF=""TCP_BARRICADES_CONST"";SELVIEW 1"

    CadInputQueue.SendKeyin "OF=""Survey_Traverse"";SELVIEW 1"

    CadInputQueue.SendKeyin "OF=""Survey_Setups"";SELVIEW 1"

    CadInputQueue.SendKeyin "OF=""Survey_Observations"";SELVIEW 1"

    CadInputQueue.SendKeyin "OF=""Survey_Control Points"";SELVIEW 1"

    CadInputQueue.SendKeyin "OF=""Subgrade"";SELVIEW 1"

    CadInputQueue.SendKeyin "OF=""STATUS_STATUS"";SELVIEW 1"

    CadInputQueue.SendKeyin "OF=""STATUS_OFFICE"";SELVIEW 1"

    CadInputQueue.SendKeyin "OF=""STATUS_CONSTRUCTION"";SELVIEW 1"

    CadInputQueue.SendKeyin "OF=""STATUS_CONCEPTUAL"";SELVIEW 1"

    CadInputQueue.SendKeyin "OF=""STATUS_CHECKPRINTS"";SELVIEW 1"

    CadInputQueue.SendKeyin "OF=""STATUS_BACKCHECKS"";SELVIEW 1"

    CadInputQueue.SendKeyin "OF=""STATUS_ASBUILT"";SELVIEW 1"

    CadInputQueue.SendKeyin "OF=""STATUS_60"";SELVIEW 1"

    CadInputQueue.SendKeyin "OF=""STATUS_30"";SELVIEW 1"

    CadInputQueue.SendKeyin "OF=""SRV_STAID_TAG"";SELVIEW 1"

    CadInputQueue.SendKeyin "OF=""SRV_FEDAID_TAG"";SELVIEW 1"

    CadInputQueue.SendKeyin "OF=""SMD_PROPERTY"";SELVIEW 1"

    CadInputQueue.SendKeyin "OF=""SLOPE_STAKES_TX"";SELVIEW 1"

    CadInputQueue.SendKeyin "OF=""SLOPE_STAKES_TRANSITION"";SELVIEW 1"

    CadInputQueue.SendKeyin "OF=""SLOPE_STAKES_FILL"";SELVIEW 1"

    CadInputQueue.SendKeyin "OF=""SLOPE_STAKES_CUT"";SELVIEW 1"

    CadInputQueue.SendKeyin "OF=""Site_Temp_Construction"";SELVIEW 1"

    CadInputQueue.SendKeyin "OF=""Site_Pad"";SELVIEW 1"

    CadInputQueue.SendKeyin "OF=""SIGNS_TX"";SELVIEW 1"

    CadInputQueue.SendKeyin "OF=""SIGNS_OVERHEAD"";SELVIEW 1"

    CadInputQueue.SendKeyin "OF=""SIGNS"";SELVIEW 1"

    CadInputQueue.SendKeyin "OF=""SIGNAL_TX"";SELVIEW 1"

    CadInputQueue.SendKeyin "OF=""SIGNAL_POLES"";SELVIEW 1"

    CadInputQueue.SendKeyin "OF=""SIGNAL_HEADS"";SELVIEW 1"

    CadInputQueue.SendKeyin "OF=""SIGNAL_DEVICES"";SELVIEW 1"

    CadInputQueue.SendKeyin "OF=""SHEET_WORK_NUMBER"";SELVIEW 1"

    CadInputQueue.SendKeyin "OF=""SHEET_TITLE_PLANS_STAGE"";SELVIEW 1"

    CadInputQueue.SendKeyin "OF=""SHEET_TITLE_BLOCK_TX"";SELVIEW 1"

    CadInputQueue.SendKeyin "OF=""SHEET_TITLE_BLOCK"";SELVIEW 1"

    CadInputQueue.SendKeyin "OF=""SHEET_STAMPS_TX"";SELVIEW 1"

    CadInputQueue.SendKeyin "OF=""SHEET_STAMPS"";SELVIEW 1"

    CadInputQueue.SendKeyin "OF=""SHEET_SCALE_BAR"";SELVIEW 1"

    CadInputQueue.SendKeyin "OF=""SHEET_REVISION_ADDENDUM"";SELVIEW 1"

    CadInputQueue.SendKeyin "OF=""SHEET_REVISION_2ND_ORDER"";SELVIEW 1"

    CadInputQueue.SendKeyin "OF=""SHEET_REVISION_1ST_ORDER"";SELVIEW 1"

    CadInputQueue.SendKeyin "OF=""SHEET_QUANTITY_TABLE"";SELVIEW 1"

    CadInputQueue.SendKeyin "OF=""SHEET_QUANTITY_RECAP_BLKS_TX"";SELVIEW 1"

    CadInputQueue.SendKeyin "OF=""SHEET_QUANTITY_RECAP_BLKS_BORDERS"";SELVIEW 1"

    CadInputQueue.SendKeyin "OF=""SHEET_PROJ_NUMBER"";SELVIEW 1"

    CadInputQueue.SendKeyin "OF=""SHEET_PRELIM"";SELVIEW 1"

    CadInputQueue.SendKeyin "OF=""SHEET_PLOTTING_SHAPE"";SELVIEW 1"

    CadInputQueue.SendKeyin "OF=""SHEET_PLOT_CTRL_BORDER_GUIDES"";SELVIEW 1"

    CadInputQueue.SendKeyin "OF=""SHEET_PLOT_CTRL_BORDER"";SELVIEW 1"

    CadInputQueue.SendKeyin "OF=""SHEET_PAGE_NUMBER"";SELVIEW 1"

    CadInputQueue.SendKeyin "OF=""SHEET_NOTE_TX"";SELVIEW 1"

    CadInputQueue.SendKeyin "OF=""SHEET_NORTH_ARROW"";SELVIEW 1"

    CadInputQueue.SendKeyin "OF=""SHEET_MDOT_LOGO"";SELVIEW 1"

    CadInputQueue.SendKeyin "OF=""SHEET_MATCH_LINES"";SELVIEW 1"

    CadInputQueue.SendKeyin "OF=""SHEET_LOGO"";SELVIEW 1"

    CadInputQueue.SendKeyin "OF=""SHEET_DETAILS_WRK5"";SELVIEW 1"

    CadInputQueue.SendKeyin "OF=""SHEET_DETAILS_WRK4"";SELVIEW 1"

    CadInputQueue.SendKeyin "OF=""SHEET_DETAILS_WRK3"";SELVIEW 1"

    CadInputQueue.SendKeyin "OF=""SHEET_DETAILS_WRK2"";SELVIEW 1"

    CadInputQueue.SendKeyin "OF=""SHEET_DETAILS_WRK1"";SELVIEW 1"

    CadInputQueue.SendKeyin "OF=""SHEET_DATE_DGN_TX"";SELVIEW 1"

    CadInputQueue.SendKeyin "OF=""SHEET_CONSULTANT_STAMP"";SELVIEW 1"

    CadInputQueue.SendKeyin "OF=""SHEET_BORDER_TX"";SELVIEW 1"

    CadInputQueue.SendKeyin "OF=""SHEET_BORDER_GRIDS"";SELVIEW 1"

    CadInputQueue.SendKeyin "OF=""Sawcut_Line"";SELVIEW 1"

    CadInputQueue.SendKeyin "OF=""SAFETY_DEV_TX"";SELVIEW 1"

    CadInputQueue.SendKeyin "OF=""SAFETY_DEV_GUARDRAIL_RT"";SELVIEW 1"

    CadInputQueue.SendKeyin "OF=""SAFETY_DEV_GUARDRAIL_LT"";SELVIEW 1"

    CadInputQueue.SendKeyin "OF=""SAFETY_DEV_BARRIERS"";SELVIEW 1"

    CadInputQueue.SendKeyin "OF=""SAFETY_DEV_ATTENUATORS"";SELVIEW 1"

    CadInputQueue.SendKeyin "OF=""ROW_TX_BOLD"";SELVIEW 1"

    CadInputQueue.SendKeyin "OF=""ROW_TX"";SELVIEW 1"

    CadInputQueue.SendKeyin "OF=""ROW_REVISION_DATA"";SELVIEW 1"

    CadInputQueue.SendKeyin "OF=""ROW_OTHR_SOLID"";SELVIEW 1"

    CadInputQueue.SendKeyin "OF=""ROW_OTHR_DASH"";SELVIEW 1"

    CadInputQueue.SendKeyin "OF=""ROW_NOPLT"";SELVIEW 1"

    CadInputQueue.SendKeyin "OF=""ROW_NO_ACCESS_LIMITS"";SELVIEW 1"

    CadInputQueue.SendKeyin "OF=""ROW_MARKERS"";SELVIEW 1"

    CadInputQueue.SendKeyin "OF=""ROW_LINES"";SELVIEW 1"

    CadInputQueue.SendKeyin "OF=""ROW_FENCING"";SELVIEW 1"

    CadInputQueue.SendKeyin "OF=""ROW_EASEMENTS"";SELVIEW 1"

    CadInputQueue.SendKeyin "OF=""ROW_EASEMENT_MARKERS"";SELVIEW 1"

    CadInputQueue.SendKeyin "OF=""ROW_CORP_LINE"";SELVIEW 1"

    CadInputQueue.SendKeyin "OF=""ROW_BORD_TX_LIGT_1"";SELVIEW 1"

    CadInputQueue.SendKeyin "OF=""ROW_BORD_TX_LIGT"";SELVIEW 1"

    CadInputQueue.SendKeyin "OF=""ROW_BORD_TX_BOLD"";SELVIEW 1"

    CadInputQueue.SendKeyin "OF=""ROW_BORD_SHPE_PLT"";SELVIEW 1"

    CadInputQueue.SendKeyin "OF=""ROW_BORD_SHPE_CLP"";SELVIEW 1"

    CadInputQueue.SendKeyin "OF=""ROW_BORD_OUTLINE"";SELVIEW 1"

    CadInputQueue.SendKeyin "OF=""ROW_BORD_LGND_TX"";SELVIEW 1"

    CadInputQueue.SendKeyin "OF=""Road_Traffic Cones"";SELVIEW 1"

    CadInputQueue.SendKeyin "OF=""Road_Reflector_Post"";SELVIEW 1"

    CadInputQueue.SendKeyin "OF=""Road_Jersey Barrier"";SELVIEW 1"

    CadInputQueue.SendKeyin "OF=""Road_Guardrail"";SELVIEW 1"

    CadInputQueue.SendKeyin "OF=""Road_Driveway"";SELVIEW 1"

    CadInputQueue.SendKeyin "OF=""Road_Construction Barrels"";SELVIEW 1"

    CadInputQueue.SendKeyin "OF=""Road_Channelizer Cones"";SELVIEW 1"

    CadInputQueue.SendKeyin "OF=""Road_Cable Barrier"";SELVIEW 1"

    CadInputQueue.SendKeyin "OF=""Road_Barrier"";SELVIEW 1"

    CadInputQueue.SendKeyin "OF=""REMOVAL_OF_PAVMT_HATCH"";SELVIEW 1"

    CadInputQueue.SendKeyin "OF=""RB_NoClearing"";SELVIEW 1"

    CadInputQueue.SendKeyin "OF=""RB_ClearingGrubbing"";SELVIEW 1"

    CadInputQueue.SendKeyin "OF=""RB_AsphaltEmbankment"";SELVIEW 1"

    CadInputQueue.SendKeyin "OF=""RB_AllowableActivities"";SELVIEW 1"

    CadInputQueue.SendKeyin "OF=""RASTER_CLIP"";SELVIEW 1"

    CadInputQueue.SendKeyin "OF=""RASTER"";SELVIEW 1"

    CadInputQueue.SendKeyin "OF=""QUAN_SIDEWALK"";SELVIEW 1"

    CadInputQueue.SendKeyin "OF=""QUAN_REMOVAL"";SELVIEW 1"

    CadInputQueue.SendKeyin "OF=""QUAN_PAVEMENT_EXCLUDE"";SELVIEW 1"

    CadInputQueue.SendKeyin "OF=""QUAN_PAVEMENT_CONCRETE"";SELVIEW 1"

    CadInputQueue.SendKeyin "OF=""QUAN_PAVEMENT_ASPHALT"";SELVIEW 1"

    CadInputQueue.SendKeyin "OF=""QUAN_ISLAND"";SELVIEW 1"

    CadInputQueue.SendKeyin "OF=""QUAN_DRIVE"";SELVIEW 1"

    CadInputQueue.SendKeyin "OF=""QUAN_CLEARING"";SELVIEW 1"

    CadInputQueue.SendKeyin "OF=""QUAN_BRIDGEEND"";SELVIEW 1"

    CadInputQueue.SendKeyin "OF=""PS_WORKFRAME"";SELVIEW 1"

    CadInputQueue.SendKeyin "OF=""PS_WELD"";SELVIEW 1"

    CadInputQueue.SendKeyin "OF=""PS_TEXT"";SELVIEW 1"

    CadInputQueue.SendKeyin "OF=""PS_SOLID"";SELVIEW 1"

    CadInputQueue.SendKeyin "OF=""PS_SHAPE"";SELVIEW 1"

    CadInputQueue.SendKeyin "OF=""PS_RoofWall"";SELVIEW 1"

    CadInputQueue.SendKeyin "OF=""PS_POS"";SELVIEW 1"

    CadInputQueue.SendKeyin "OF=""PS_PLATE"";SELVIEW 1"

    CadInputQueue.SendKeyin "OF=""PS_OBJECT"";SELVIEW 1"

    CadInputQueue.SendKeyin "OF=""PS_MID"";SELVIEW 1"

    CadInputQueue.SendKeyin "OF=""PS_KOTE"";SELVIEW 1"

    CadInputQueue.SendKeyin "OF=""PS_HIDDEN"";SELVIEW 1"

    CadInputQueue.SendKeyin "OF=""PS_HATCH"";SELVIEW 1"

    CadInputQueue.SendKeyin "OF=""PS_Elev_flag"";SELVIEW 1"

    CadInputQueue.SendKeyin "OF=""PS_DIM"";SELVIEW 1"

    CadInputQueue.SendKeyin "OF=""PS_DAWA"";SELVIEW 1"

    CadInputQueue.SendKeyin "OF=""PS_CONST"";SELVIEW 1"

    CadInputQueue.SendKeyin "OF=""PS_BOLT"";SELVIEW 1"

    CadInputQueue.SendKeyin "OF=""PROFILES_TX_VPI_2"";SELVIEW 1"

    CadInputQueue.SendKeyin "OF=""PROFILES_TX_VPI"";SELVIEW 1"

    CadInputQueue.SendKeyin "OF=""PROFILES_TX_STRIP_2"";SELVIEW 1"

    CadInputQueue.SendKeyin "OF=""PROFILES_TX_STRIP"";SELVIEW 1"

    CadInputQueue.SendKeyin "OF=""PROFILES_TX_GRADES_2"";SELVIEW 1"

    CadInputQueue.SendKeyin "OF=""PROFILES_TX_GRADES"";SELVIEW 1"

    CadInputQueue.SendKeyin "OF=""PROFILES_TX"";SELVIEW 1"

    CadInputQueue.SendKeyin "OF=""PROFILES_STA"";SELVIEW 1"

    CadInputQueue.SendKeyin "OF=""PROFILES_ELEV"";SELVIEW 1"

    CadInputQueue.SendKeyin "OF=""PROFILES_DCH_3_TX_VPI"";SELVIEW 1"

    CadInputQueue.SendKeyin "OF=""PROFILES_DCH_3_TX_STRIP"";SELVIEW 1"

    CadInputQueue.SendKeyin "OF=""PROFILES_DCH_3_TX_GRADES"";SELVIEW 1"

    CadInputQueue.SendKeyin "OF=""PROFILES_DCH_3"";SELVIEW 1"

    CadInputQueue.SendKeyin "OF=""PROFILES_DCH_2_TX_VPI"";SELVIEW 1"

    CadInputQueue.SendKeyin "OF=""PROFILES_DCH_2_TX_STRIP"";SELVIEW 1"

    CadInputQueue.SendKeyin "OF=""PROFILES_DCH_2_TX_GRADES"";SELVIEW 1"

    CadInputQueue.SendKeyin "OF=""PROFILES_DCH_2"";SELVIEW 1"

    CadInputQueue.SendKeyin "OF=""PROFILES_DCH_1_TX_VPI"";SELVIEW 1"

    CadInputQueue.SendKeyin "OF=""PROFILES_DCH_1_TX_STRIP"";SELVIEW 1"

    CadInputQueue.SendKeyin "OF=""PROFILES_DCH_1_TX_GRADES"";SELVIEW 1"

    CadInputQueue.SendKeyin "OF=""PROFILES_DCH_1"";SELVIEW 1"

    CadInputQueue.SendKeyin "OF=""PROFILES_2"";SELVIEW 1"

    CadInputQueue.SendKeyin "OF=""PROFILES_1"";SELVIEW 1"

    CadInputQueue.SendKeyin "OF=""Profile_Special_Ditch_R"";SELVIEW 1"

    CadInputQueue.SendKeyin "OF=""Profile_Special_Ditch_L"";SELVIEW 1"

    CadInputQueue.SendKeyin "OF=""PROFILE_DRAINAGE_TX"";SELVIEW 1"

    CadInputQueue.SendKeyin "OF=""PROFILE_DRAINAGE"";SELVIEW 1"

    CadInputQueue.SendKeyin "OF=""PROFILE_CELL"";SELVIEW 1"

    CadInputQueue.SendKeyin "OF=""POINT_ROW"";SELVIEW 1"

    CadInputQueue.SendKeyin "OF=""POINT_PROPERTY_CORNER"";SELVIEW 1"

    CadInputQueue.SendKeyin "OF=""PM_STRIPE_TX"";SELVIEW 1"

    CadInputQueue.SendKeyin "OF=""PM_STRIPE"";SELVIEW 1"

    CadInputQueue.SendKeyin "OF=""PM_RUMBLE_STRIP"";SELVIEW 1"

    CadInputQueue.SendKeyin "OF=""PM_RAISED_MARKERS_TX"";SELVIEW 1"

    CadInputQueue.SendKeyin "OF=""PM_RAISED_MARKERS"";SELVIEW 1"

    CadInputQueue.SendKeyin "OF=""PC_WALL"";SELVIEW 1"

    CadInputQueue.SendKeyin "OF=""PC_STRIPFOOTING"";SELVIEW 1"

    CadInputQueue.SendKeyin "OF=""PC_SLAB"";SELVIEW 1"

    CadInputQueue.SendKeyin "OF=""PC_REBAR"";SELVIEW 1"

    CadInputQueue.SendKeyin "OF=""PC_PADFOOTING"";SELVIEW 1"

    CadInputQueue.SendKeyin "OF=""PC_OBJECT"";SELVIEW 1"

    CadInputQueue.SendKeyin "OF=""PC_MARKER"";SELVIEW 1"

    CadInputQueue.SendKeyin "OF=""PC_COVER"";SELVIEW 1"

    CadInputQueue.SendKeyin "OF=""PC_CONCRETE"";SELVIEW 1"

    CadInputQueue.SendKeyin "OF=""PC_COLUMN"";SELVIEW 1"

    CadInputQueue.SendKeyin "OF=""PC_BEAM"";SELVIEW 1"

    CadInputQueue.SendKeyin "OF=""Pavement Marking Yellow"";SELVIEW 1"

    CadInputQueue.SendKeyin "OF=""Pavement Marking White"";SELVIEW 1"

    CadInputQueue.SendKeyin "OF=""PATTERN_DETAILS"";SELVIEW 1"

    CadInputQueue.SendKeyin "OF=""PARCEL_POINT"";SELVIEW 1"

    CadInputQueue.SendKeyin "OF=""Parcel"";SELVIEW 1"

    CadInputQueue.SendKeyin "OF=""OBM_Wingwalls"";SELVIEW 1"

    CadInputQueue.SendKeyin "OF=""OBM_Wet Joint"";SELVIEW 1"

    CadInputQueue.SendKeyin "OF=""OBM_Tubs"";SELVIEW 1"

    CadInputQueue.SendKeyin "OF=""OBM_Tub girder"";SELVIEW 1"

    CadInputQueue.SendKeyin "OF=""OBM_Tendon_centerline"";SELVIEW 1"

    CadInputQueue.SendKeyin "OF=""OBM_Tendon"";SELVIEW 1"

    CadInputQueue.SendKeyin "OF=""OBM_SupportLines"";SELVIEW 1"

    CadInputQueue.SendKeyin "OF=""OBM_Struts"";SELVIEW 1"

    CadInputQueue.SendKeyin "OF=""OBM_Stiffeners"";SELVIEW 1"

    CadInputQueue.SendKeyin "OF=""OBM_Sleeper_Slab"";SELVIEW 1"

    CadInputQueue.SendKeyin "OF=""OBM_Shear_Stud"";SELVIEW 1"

    CadInputQueue.SendKeyin "OF=""OBM_Segment"";SELVIEW 1"

    CadInputQueue.SendKeyin "OF=""OBM_Seg_Typical"";SELVIEW 1"

    CadInputQueue.SendKeyin "OF=""OBM_Seg_PierSegment"";SELVIEW 1"

    CadInputQueue.SendKeyin "OF=""OBM_Seg_Expansion"";SELVIEW 1"

    CadInputQueue.SendKeyin "OF=""OBM_Seg_Closure"";SELVIEW 1"

    CadInputQueue.SendKeyin "OF=""OBM_Point"";SELVIEW 1"

    CadInputQueue.SendKeyin "OF=""OBM_Plate"";SELVIEW 1"

    CadInputQueue.SendKeyin "OF=""OBM_Piles_steel"";SELVIEW 1"

    CadInputQueue.SendKeyin "OF=""OBM_Piles_concrete"";SELVIEW 1"

    CadInputQueue.SendKeyin "OF=""OBM_Piers"";SELVIEW 1"

    CadInputQueue.SendKeyin "OF=""OBM_Paving_Bracket"";SELVIEW 1"

    CadInputQueue.SendKeyin "OF=""OBM_Haunch"";SELVIEW 1"

    CadInputQueue.SendKeyin "OF=""OBM_GroutPad"";SELVIEW 1"

    CadInputQueue.SendKeyin "OF=""OBM_GirderSteel"";SELVIEW 1"

    CadInputQueue.SendKeyin "OF=""OBM_GirderConcrete"";SELVIEW 1"

    CadInputQueue.SendKeyin "OF=""OBM_Girder"";SELVIEW 1"

    CadInputQueue.SendKeyin "OF=""OBM_Footings"";SELVIEW 1"

    CadInputQueue.SendKeyin "OF=""OBM_Filler_Plate"";SELVIEW 1"

    CadInputQueue.SendKeyin "OF=""OBM_Field_Splice"";SELVIEW 1"

    CadInputQueue.SendKeyin "OF=""OBM_FC_ConstructionLines"";SELVIEW 1"

    CadInputQueue.SendKeyin "OF=""OBM_Excavation"";SELVIEW 1"

    CadInputQueue.SendKeyin "OF=""OBM_Dummy_Deck"";SELVIEW 1"

    CadInputQueue.SendKeyin "OF=""OBM_Diaphragm_Concrete"";SELVIEW 1"

    CadInputQueue.SendKeyin "OF=""OBM_Deck"";SELVIEW 1"

    CadInputQueue.SendKeyin "OF=""OBM_D_WingWall_Piles"";SELVIEW 1"

    CadInputQueue.SendKeyin "OF=""OBM_D_WingWall_Footing"";SELVIEW 1"

    CadInputQueue.SendKeyin "OF=""OBM_D_WingWall"";SELVIEW 1"

    CadInputQueue.SendKeyin "OF=""OBM_D_Unit_Label"";SELVIEW 1"

    CadInputQueue.SendKeyin "OF=""OBM_D_SupportLines_Text"";SELVIEW 1"

    CadInputQueue.SendKeyin "OF=""OBM_D_Stiffeners"";SELVIEW 1"

    CadInputQueue.SendKeyin "OF=""OBM_D_SleeperSlab"";SELVIEW 1"

    CadInputQueue.SendKeyin "OF=""OBM_D_Shear_Studs"";SELVIEW 1"

    CadInputQueue.SendKeyin "OF=""OBM_D_Segmental_Lines_Text"";SELVIEW 1"

    CadInputQueue.SendKeyin "OF=""OBM_D_Segmental_Deck_Outline"";SELVIEW 1"

    CadInputQueue.SendKeyin "OF=""OBM_D_Reports_Lines"";SELVIEW 1"

    CadInputQueue.SendKeyin "OF=""OBM_D_Piles_Arrow_Markers"";SELVIEW 1"

    CadInputQueue.SendKeyin "OF=""OBM_D_Piles"";SELVIEW 1"

    CadInputQueue.SendKeyin "OF=""OBM_D_Pads_or_Plates"";SELVIEW 1"

    CadInputQueue.SendKeyin "OF=""OBM_D_Footing"";SELVIEW 1"

    CadInputQueue.SendKeyin "OF=""OBM_D_Field_Splice"";SELVIEW 1"

    CadInputQueue.SendKeyin "OF=""OBM_D_Diaphragm_Concrete"";SELVIEW 1"

    CadInputQueue.SendKeyin "OF=""OBM_D_Deck_Outline"";SELVIEW 1"

    CadInputQueue.SendKeyin "OF=""OBM_D_CrossFrames"";SELVIEW 1"

    CadInputQueue.SendKeyin "OF=""OBM_D_Column"";SELVIEW 1"

    CadInputQueue.SendKeyin "OF=""OBM_D_Cap"";SELVIEW 1"

    CadInputQueue.SendKeyin "OF=""OBM_D_Bridge_Decorations"";SELVIEW 1"

    CadInputQueue.SendKeyin "OF=""OBM_D_Bearings"";SELVIEW 1"

    CadInputQueue.SendKeyin "OF=""OBM_D_Bearing_Seats"";SELVIEW 1"

    CadInputQueue.SendKeyin "OF=""OBM_D_Bearing_Group_Text"";SELVIEW 1"

    CadInputQueue.SendKeyin "OF=""OBM_D_Bearing_Group"";SELVIEW 1"

    CadInputQueue.SendKeyin "OF=""OBM_D_Beam_PL_Offset"";SELVIEW 1"

    CadInputQueue.SendKeyin "OF=""OBM_D_Beam_Layout_Text"";SELVIEW 1"

    CadInputQueue.SendKeyin "OF=""OBM_D_Beam_Layout"";SELVIEW 1"

    CadInputQueue.SendKeyin "OF=""OBM_D_Beam_End"";SELVIEW 1"

    CadInputQueue.SendKeyin "OF=""OBM_D_Barrier_Outline"";SELVIEW 1"

    CadInputQueue.SendKeyin "OF=""OBM_D_ApproachSlab_Outline"";SELVIEW 1"

    CadInputQueue.SendKeyin "OF=""OBM_D_ApproachRefLine_text"";SELVIEW 1"

    CadInputQueue.SendKeyin "OF=""OBM_CrossFrames"";SELVIEW 1"

    CadInputQueue.SendKeyin "OF=""OBM_Columns"";SELVIEW 1"

    CadInputQueue.SendKeyin "OF=""OBM_CheekWall"";SELVIEW 1"

    CadInputQueue.SendKeyin "OF=""OBM_Caps"";SELVIEW 1"

    CadInputQueue.SendKeyin "OF=""OBM_Bolts"";SELVIEW 1"

    CadInputQueue.SendKeyin "OF=""OBM_BEP_Barrier"";SELVIEW 1"

    CadInputQueue.SendKeyin "OF=""OBM_Bent_Text"";SELVIEW 1"

    CadInputQueue.SendKeyin "OF=""OBM_Bent_Location"";SELVIEW 1"

    CadInputQueue.SendKeyin "OF=""OBM_Bearings"";SELVIEW 1"

    CadInputQueue.SendKeyin "OF=""OBM_Bearing_Seats"";SELVIEW 1"

    CadInputQueue.SendKeyin "OF=""OBM_Barriers"";SELVIEW 1"

    CadInputQueue.SendKeyin "OF=""OBM_Auxiliary"";SELVIEW 1"

    CadInputQueue.SendKeyin "OF=""OBM_Approach_Slab"";SELVIEW 1"

    CadInputQueue.SendKeyin "OF=""OBM_Approach_Ref_Line"";SELVIEW 1"

    CadInputQueue.SendKeyin "OF=""OBM_Abutments"";SELVIEW 1"

    CadInputQueue.SendKeyin "OF=""OBM_Abutment_WingWall"";SELVIEW 1"

    CadInputQueue.SendKeyin "OF=""MISCELLANOUS"";SELVIEW 1"

    CadInputQueue.SendKeyin "OF=""Matchline"";SELVIEW 1"

    CadInputQueue.SendKeyin "OF=""Level 60"";SELVIEW 1"

    CadInputQueue.SendKeyin "OF=""Level 17"";SELVIEW 1"

    CadInputQueue.SendKeyin "OF=""Level 1"";SELVIEW 1"

    CadInputQueue.SendKeyin "OF=""ITS_TYP_DTL"";SELVIEW 1"

    CadInputQueue.SendKeyin "OF=""ITS_SCHD_QTY"";SELVIEW 1"

    CadInputQueue.SendKeyin "OF=""ITS_PROP_WARN_SIGN"";SELVIEW 1"

    CadInputQueue.SendKeyin "OF=""ITS_PROP_SURFACE_PLBX"";SELVIEW 1"

    CadInputQueue.SendKeyin "OF=""ITS_PROP_STOP_BAR"";SELVIEW 1"

    CadInputQueue.SendKeyin "OF=""ITS_PROP_SGNL_SUPT"";SELVIEW 1"

    CadInputQueue.SendKeyin "OF=""ITS_PROP_SGNL_SIGN"";SELVIEW 1"

    CadInputQueue.SendKeyin "OF=""ITS_PROP_SGNL_RECEIVER"";SELVIEW 1"

    CadInputQueue.SendKeyin "OF=""ITS_PROP_SGNL_POLE"";SELVIEW 1"

    CadInputQueue.SendKeyin "OF=""ITS_PROP_SGNL_PLBX"";SELVIEW 1"

    CadInputQueue.SendKeyin "OF=""ITS_PROP_SGNL_INT"";SELVIEW 1"

    CadInputQueue.SendKeyin "OF=""ITS_PROP_SGNL_HEAD"";SELVIEW 1"

    CadInputQueue.SendKeyin "OF=""ITS_PROP_SGNL_FLHR"";SELVIEW 1"

    CadInputQueue.SendKeyin "OF=""ITS_PROP_SGNL_DETECTOR_MAG"";SELVIEW 1"

    CadInputQueue.SendKeyin "OF=""ITS_PROP_SGNL_DETECTOR_LOOP"";SELVIEW 1"

    CadInputQueue.SendKeyin "OF=""ITS_PROP_SGNL_DETECTOR"";SELVIEW 1"

    CadInputQueue.SendKeyin "OF=""ITS_PROP_SGNL_CODT"";SELVIEW 1"

    CadInputQueue.SendKeyin "OF=""ITS_PROP_SGNL_CABT"";SELVIEW 1"

    CadInputQueue.SendKeyin "OF=""ITS_PROP_SGNL_CABLE_UNDERGROUND"";SELVIEW 1"

    CadInputQueue.SendKeyin "OF=""ITS_PROP_SGNL_AUX"";SELVIEW 1"

    CadInputQueue.SendKeyin "OF=""ITS_PROP_SGNL_ARM"";SELVIEW 1"

    CadInputQueue.SendKeyin "OF=""ITS_PROP_RWIS"";SELVIEW 1"

    CadInputQueue.SendKeyin "OF=""ITS_PROP_REGY_SIGN"";SELVIEW 1"

    CadInputQueue.SendKeyin "OF=""ITS_PROP_RDS"";SELVIEW 1"

    CadInputQueue.SendKeyin "OF=""ITS_PROP_POWER_POLE"";SELVIEW 1"

    CadInputQueue.SendKeyin "OF=""ITS_PROP_GUID_SIGN"";SELVIEW 1"

    CadInputQueue.SendKeyin "OF=""ITS_PROP_FIBER_DROP_CABLE"";SELVIEW 1"

    CadInputQueue.SendKeyin "OF=""ITS_PROP_FIBER_CABLE_UNDERGROUND"";SELVIEW 1"

    CadInputQueue.SendKeyin "OF=""ITS_PROP_FIBER_CABLE_OVERHEAD"";SELVIEW 1"

    CadInputQueue.SendKeyin "OF=""ITS_PROP_ELEC_PLBX"";SELVIEW 1"

    CadInputQueue.SendKeyin "OF=""ITS_PROP_ELEC_METER"";SELVIEW 1"

    CadInputQueue.SendKeyin "OF=""ITS_PROP_ELEC_DISBOX"";SELVIEW 1"

    CadInputQueue.SendKeyin "OF=""ITS_PROP_ELEC_CABLE_UNDERGROUND"";SELVIEW 1"

    CadInputQueue.SendKeyin "OF=""ITS_PROP_ELEC_CABLE_OVERHEAD"";SELVIEW 1"

    CadInputQueue.SendKeyin "OF=""ITS_PROP_DMS"";SELVIEW 1"

    CadInputQueue.SendKeyin "OF=""ITS_PROP_COMM_VAULT"";SELVIEW 1"

    CadInputQueue.SendKeyin "OF=""ITS_PROP_COMM_PLBX"";SELVIEW 1"

    CadInputQueue.SendKeyin "OF=""ITS_PROP_COMM_HUT"";SELVIEW 1"

    CadInputQueue.SendKeyin "OF=""ITS_PROP_CCTV_CAMERA"";SELVIEW 1"

    CadInputQueue.SendKeyin "OF=""ITS_PROP_CAMERA_POLE"";SELVIEW 1"

    CadInputQueue.SendKeyin "OF=""ITS_PROP_BDS"";SELVIEW 1"

    CadInputQueue.SendKeyin "OF=""ITS_EXST_WARN_SIGN"";SELVIEW 1"

    CadInputQueue.SendKeyin "OF=""ITS_EXST_SURFACE_PLBX"";SELVIEW 1"

    CadInputQueue.SendKeyin "OF=""ITS_EXST_STOP_BAR"";SELVIEW 1"

    CadInputQueue.SendKeyin "OF=""ITS_EXST_SGNL_SUPT"";SELVIEW 1"

    CadInputQueue.SendKeyin "OF=""ITS_EXST_SGNL_SIGN"";SELVIEW 1"

    CadInputQueue.SendKeyin "OF=""ITS_EXST_SGNL_RECEIVER"";SELVIEW 1"

    CadInputQueue.SendKeyin "OF=""ITS_EXST_SGNL_POLE"";SELVIEW 1"

    CadInputQueue.SendKeyin "OF=""ITS_EXST_SGNL_PLBX"";SELVIEW 1"

    CadInputQueue.SendKeyin "OF=""ITS_EXST_SGNL_INT"";SELVIEW 1"

    CadInputQueue.SendKeyin "OF=""ITS_EXST_SGNL_HEAD"";SELVIEW 1"

    CadInputQueue.SendKeyin "OF=""ITS_EXST_SGNL_FLHR"";SELVIEW 1"

    CadInputQueue.SendKeyin "OF=""ITS_EXST_SGNL_DETECTOR_MAG"";SELVIEW 1"

    CadInputQueue.SendKeyin "OF=""ITS_EXST_SGNL_DETECTOR_LOOP"";SELVIEW 1"

    CadInputQueue.SendKeyin "OF=""ITS_EXST_SGNL_DETECTOR"";SELVIEW 1"

    CadInputQueue.SendKeyin "OF=""ITS_EXST_SGNL_CODT"";SELVIEW 1"

    CadInputQueue.SendKeyin "OF=""ITS_EXST_SGNL_CABT"";SELVIEW 1"

    CadInputQueue.SendKeyin "OF=""ITS_EXST_SGNL_CABLE_UNDERGROUND"";SELVIEW 1"

    CadInputQueue.SendKeyin "OF=""ITS_EXST_SGNL_AUX"";SELVIEW 1"

    CadInputQueue.SendKeyin "OF=""ITS_EXST_SGNL_ARM"";SELVIEW 1"

    CadInputQueue.SendKeyin "OF=""ITS_EXST_RWIS"";SELVIEW 1"

    CadInputQueue.SendKeyin "OF=""ITS_EXST_REGY_SIGN"";SELVIEW 1"

    CadInputQueue.SendKeyin "OF=""ITS_EXST_RDS"";SELVIEW 1"

    CadInputQueue.SendKeyin "OF=""ITS_EXST_POWER_POLE"";SELVIEW 1"

    CadInputQueue.SendKeyin "OF=""ITS_EXST_GUID_SIGN"";SELVIEW 1"

    CadInputQueue.SendKeyin "OF=""ITS_EXST_FIBER_DROP_CABLE"";SELVIEW 1"

    CadInputQueue.SendKeyin "OF=""ITS_EXST_FIBER_CABLE_UNDERGROUND"";SELVIEW 1"

    CadInputQueue.SendKeyin "OF=""ITS_EXST_FIBER_CABLE_OVERHEAD"";SELVIEW 1"

    CadInputQueue.SendKeyin "OF=""ITS_EXST_ELEC_PLBX"";SELVIEW 1"

    CadInputQueue.SendKeyin "OF=""ITS_EXST_ELEC_METER"";SELVIEW 1"

    CadInputQueue.SendKeyin "OF=""ITS_EXST_ELEC_DISBOX"";SELVIEW 1"

    CadInputQueue.SendKeyin "OF=""ITS_EXST_ELEC_CABLE_UNDERGROUND"";SELVIEW 1"

    CadInputQueue.SendKeyin "OF=""ITS_EXST_ELEC_CABLE_OVERHEAD"";SELVIEW 1"

    CadInputQueue.SendKeyin "OF=""ITS_EXST_DMS"";SELVIEW 1"

    CadInputQueue.SendKeyin "OF=""ITS_EXST_COMM_VAULT"";SELVIEW 1"

    CadInputQueue.SendKeyin "OF=""ITS_EXST_COMM_PLBX"";SELVIEW 1"

    CadInputQueue.SendKeyin "OF=""ITS_EXST_COMM_HUT"";SELVIEW 1"

    CadInputQueue.SendKeyin "OF=""ITS_EXST_CCTV_CAMERA"";SELVIEW 1"

    CadInputQueue.SendKeyin "OF=""ITS_EXST_CAMERA_POLE"";SELVIEW 1"

    CadInputQueue.SendKeyin "OF=""ITS_EXST_BDS"";SELVIEW 1"

    CadInputQueue.SendKeyin "OF=""ITS_ANNO_TEXT"";SELVIEW 1"

    CadInputQueue.SendKeyin "OF=""ITS_ANNO_SYMB"";SELVIEW 1"

    CadInputQueue.SendKeyin "OF=""ITS_ANNO_NPLT"";SELVIEW 1"

    CadInputQueue.SendKeyin "OF=""ITS_ANNO_NOTE"";SELVIEW 1"

    CadInputQueue.SendKeyin "OF=""ITS_ANNO_LINE"";SELVIEW 1"

    CadInputQueue.SendKeyin "OF=""ITS_ANNO_DIM"";SELVIEW 1"

    CadInputQueue.SendKeyin "OF=""ITS_ANNO_BORD"";SELVIEW 1"

    CadInputQueue.SendKeyin "OF=""Intersecting Profile"";SELVIEW 1"

    CadInputQueue.SendKeyin "OF=""INFO_LV5"";SELVIEW 1"

    CadInputQueue.SendKeyin "OF=""INFO_LV4"";SELVIEW 1"

    CadInputQueue.SendKeyin "OF=""INFO_LV3"";SELVIEW 1"

    CadInputQueue.SendKeyin "OF=""INFO_LV2"";SELVIEW 1"

    CadInputQueue.SendKeyin "OF=""INFO_LV1"";SELVIEW 1"

    CadInputQueue.SendKeyin "OF=""Grade_Veg_Grass"";SELVIEW 1"

    CadInputQueue.SendKeyin "OF=""Grade_Finished"";SELVIEW 1"

    CadInputQueue.SendKeyin "OF=""Geotechnical_Water"";SELVIEW 1"

    CadInputQueue.SendKeyin "OF=""Geotechnical_Topsoil"";SELVIEW 1"

    CadInputQueue.SendKeyin "OF=""Geotechnical_SW"";SELVIEW 1"

    CadInputQueue.SendKeyin "OF=""Geotechnical_SPT_SS"";SELVIEW 1"

    CadInputQueue.SendKeyin "OF=""Geotechnical_SPT_Other"";SELVIEW 1"

    CadInputQueue.SendKeyin "OF=""Geotechnical_Silt_Elastic"";SELVIEW 1"

    CadInputQueue.SendKeyin "OF=""Geotechnical_Silt"";SELVIEW 1"

    CadInputQueue.SendKeyin "OF=""Geotechnical_Shale"";SELVIEW 1"

    CadInputQueue.SendKeyin "OF=""Geotechnical_Sand_Well_Grade"";SELVIEW 1"

    CadInputQueue.SendKeyin "OF=""Geotechnical_Sand_Silt_Well_Grade"";SELVIEW 1"

    CadInputQueue.SendKeyin "OF=""Geotechnical_Sand_Silt_Poor_Grade"";SELVIEW 1"

    CadInputQueue.SendKeyin "OF=""Geotechnical_Sand_Silt"";SELVIEW 1"

    CadInputQueue.SendKeyin "OF=""Geotechnical_Sand_Poor_Grade"";SELVIEW 1"

    CadInputQueue.SendKeyin "OF=""Geotechnical_Sand_Clay_Well_Grade"";SELVIEW 1"

    CadInputQueue.SendKeyin "OF=""Geotechnical_Sand_Clay_Poor_Grade"";SELVIEW 1"

    CadInputQueue.SendKeyin "OF=""Geotechnical_Sand_Clay"";SELVIEW 1"

    CadInputQueue.SendKeyin "OF=""Geotechnical_Other"";SELVIEW 1"

    CadInputQueue.SendKeyin "OF=""Geotechnical_Organic"";SELVIEW 1"

    CadInputQueue.SendKeyin "OF=""Geotechnical_LS"";SELVIEW 1"

    CadInputQueue.SendKeyin "OF=""Geotechnical_Gravel_Well_Grade"";SELVIEW 1"

    CadInputQueue.SendKeyin "OF=""Geotechnical_Gravel_Silty"";SELVIEW 1"

    CadInputQueue.SendKeyin "OF=""Geotechnical_Gravel_Silt_Well_Grade"";SELVIEW 1"

    CadInputQueue.SendKeyin "OF=""Geotechnical_Gravel_Silt_Poor_Grade"";SELVIEW 1"

    CadInputQueue.SendKeyin "OF=""Geotechnical_Gravel_Poor_Grade"";SELVIEW 1"

    CadInputQueue.SendKeyin "OF=""Geotechnical_Gravel_Clay_Well_Grade"";SELVIEW 1"

    CadInputQueue.SendKeyin "OF=""Geotechnical_Gravel_Clay_Poor_Grade"";SELVIEW 1"

    CadInputQueue.SendKeyin "OF=""Geotechnical_Gravel"";SELVIEW 1"

    CadInputQueue.SendKeyin "OF=""Geotechnical_Clay_Lean"";SELVIEW 1"

    CadInputQueue.SendKeyin "OF=""Geotechnical_Clay_Gravel"";SELVIEW 1"

    CadInputQueue.SendKeyin "OF=""Geotechnical_Clay_Fat"";SELVIEW 1"

    CadInputQueue.SendKeyin "OF=""Geotechnical_Borehole_Sample"";SELVIEW 1"

    CadInputQueue.SendKeyin "OF=""Geotechnical_Borehole_Location"";SELVIEW 1"

    CadInputQueue.SendKeyin "OF=""Geom_ROW"";SELVIEW 1"

    CadInputQueue.SendKeyin "OF=""Geom_Civil_Cell_Control"";SELVIEW 1"

    CadInputQueue.SendKeyin "OF=""GEO_ZONE_NAME_DESC"";SELVIEW 1"

    CadInputQueue.SendKeyin "OF=""GEO_ZONE_NAME"";SELVIEW 1"

    CadInputQueue.SendKeyin "OF=""GEO_ZONE_DESC"";SELVIEW 1"

    CadInputQueue.SendKeyin "OF=""GEO_TYPL_BEAM"";SELVIEW 1"

    CadInputQueue.SendKeyin "OF=""GEO_TITLE_ANNO"";SELVIEW 1"

    CadInputQueue.SendKeyin "OF=""GEO_SYMB"";SELVIEW 1"

    CadInputQueue.SendKeyin "OF=""GEO_STATION_NO"";SELVIEW 1"

    CadInputQueue.SendKeyin "OF=""GEO_SOIL_STRH_TBLE"";SELVIEW 1"

    CadInputQueue.SendKeyin "OF=""GEO_SLIDE_SECT"";SELVIEW 1"

    CadInputQueue.SendKeyin "OF=""GEO_SCOUR_ELEV"";SELVIEW 1"

    CadInputQueue.SendKeyin "OF=""GEO_SCOUR_500"";SELVIEW 1"

    CadInputQueue.SendKeyin "OF=""GEO_SCOUR_100"";SELVIEW 1"

    CadInputQueue.SendKeyin "OF=""GEO_SCALE_BAR"";SELVIEW 1"

    CadInputQueue.SendKeyin "OF=""GEO_RANGE_8"";SELVIEW 1"

    CadInputQueue.SendKeyin "OF=""GEO_RANGE_3"";SELVIEW 1"

    CadInputQueue.SendKeyin "OF=""GEO_RANGE_2"";SELVIEW 1"

    CadInputQueue.SendKeyin "OF=""GEO_RANGE_1"";SELVIEW 1"

    CadInputQueue.SendKeyin "OF=""GEO_PATT_SOD"";SELVIEW 1"

    CadInputQueue.SendKeyin "OF=""GEO_PATT_SAND"";SELVIEW 1"

    CadInputQueue.SendKeyin "OF=""GEO_PATT_RIPRAP"";SELVIEW 1"

    CadInputQueue.SendKeyin "OF=""GEO_PATT_LQSL"";SELVIEW 1"

    CadInputQueue.SendKeyin "OF=""GEO_PATT_GRAVEL"";SELVIEW 1"

    CadInputQueue.SendKeyin "OF=""GEO_PATT_GRASS"";SELVIEW 1"

    CadInputQueue.SendKeyin "OF=""GEO_PATT_GRADE"";SELVIEW 1"

    CadInputQueue.SendKeyin "OF=""GEO_PATT_CRSRBL"";SELVIEW 1"

    CadInputQueue.SendKeyin "OF=""GEO_PATT_CONC"";SELVIEW 1"

    CadInputQueue.SendKeyin "OF=""GEO_NRTH_AROW"";SELVIEW 1"

    CadInputQueue.SendKeyin "OF=""GEO_NAT_GRND"";SELVIEW 1"

    CadInputQueue.SendKeyin "OF=""GEO_LINE_TERM"";SELVIEW 1"

    CadInputQueue.SendKeyin "OF=""GEO_HAMR_NOTE"";SELVIEW 1"

    CadInputQueue.SendKeyin "OF=""GEO_GRND_ZONE_NEW"";SELVIEW 1"

    CadInputQueue.SendKeyin "OF=""GEO_GRND_LINE_EXSIT"";SELVIEW 1"

    CadInputQueue.SendKeyin "OF=""GEO_GRADATION"";SELVIEW 1"

    CadInputQueue.SendKeyin "OF=""GEO_GRAD_TRI"";SELVIEW 1"

    CadInputQueue.SendKeyin "OF=""GEO_FNISH_GRAD_TEXT"";SELVIEW 1"

    CadInputQueue.SendKeyin "OF=""GEO_FINSH_GRADE"";SELVIEW 1"

    CadInputQueue.SendKeyin "OF=""GEO_EXST_BRIDGE"";SELVIEW 1"

    CadInputQueue.SendKeyin "OF=""GEO_DSGN_STAGE_50YR"";SELVIEW 1"

    CadInputQueue.SendKeyin "OF=""GEO_DESC_TEXT"";SELVIEW 1"

    CadInputQueue.SendKeyin "OF=""GEO_CNTR_LINE_SURV"";SELVIEW 1"

    CadInputQueue.SendKeyin "OF=""GEO_CNTR_LINE"";SELVIEW 1"

    CadInputQueue.SendKeyin "OF=""GEO_BRIDGE"";SELVIEW 1"

    CadInputQueue.SendKeyin "OF=""GEO_BORG_SYMB"";SELVIEW 1"

    CadInputQueue.SendKeyin "OF=""GEO_BORDER"";SELVIEW 1"

    CadInputQueue.SendKeyin "OF=""GEO_BLOG_ZONE_LINE"";SELVIEW 1"

    CadInputQueue.SendKeyin "OF=""GEO_BLOG_TEXT"";SELVIEW 1"

    CadInputQueue.SendKeyin "OF=""GEO_BLOG_FIELD_LINE"";SELVIEW 1"

    CadInputQueue.SendKeyin "OF=""GEO_BLOG"";SELVIEW 1"

    CadInputQueue.SendKeyin "OF=""GEO_BENT_TYP3_BEAM"";SELVIEW 1"

    CadInputQueue.SendKeyin "OF=""GEO_BENT_TYP2_BEAM"";SELVIEW 1"

    CadInputQueue.SendKeyin "OF=""GEO_BENT_TYP1_BEAM"";SELVIEW 1"

    CadInputQueue.SendKeyin "OF=""GEO_BENT_BT72_BEAM"";SELVIEW 1"

    CadInputQueue.SendKeyin "OF=""GEO_BENT_BT63_BEAM"";SELVIEW 1"

    CadInputQueue.SendKeyin "OF=""GEO_BENT_BT54_BEAM"";SELVIEW 1"

    CadInputQueue.SendKeyin "OF=""GEO_ANNO_GENERAL"";SELVIEW 1"

    CadInputQueue.SendKeyin "OF=""FORM_GRADE_SLOPE_LABEL"";SELVIEW 1"

    CadInputQueue.SendKeyin "OF=""FORM_GRADE_LANE_LINES"";SELVIEW 1"

    CadInputQueue.SendKeyin "OF=""FORM_GRADE_ELEV_LABEL"";SELVIEW 1"

    CadInputQueue.SendKeyin "OF=""Fence_Wrought_Iron"";SELVIEW 1"

    CadInputQueue.SendKeyin "OF=""Fence_Rod_Iron"";SELVIEW 1"

    CadInputQueue.SendKeyin "OF=""Fence_Chain_Link"";SELVIEW 1"

    CadInputQueue.SendKeyin "OF=""EASEMENT_MARKER"";SELVIEW 1"

    CadInputQueue.SendKeyin "OF=""E_Terrain_Void"";SELVIEW 1"

    CadInputQueue.SendKeyin "OF=""E_Terrain_Triangle_Vertices"";SELVIEW 1"

    CadInputQueue.SendKeyin "OF=""E_Terrain_Triangle"";SELVIEW 1"

    CadInputQueue.SendKeyin "OF=""E_Terrain_Top_Rock"";SELVIEW 1"

    CadInputQueue.SendKeyin "OF=""E_Terrain_Survey"";SELVIEW 1"

    CadInputQueue.SendKeyin "OF=""E_Terrain_SpotElevation"";SELVIEW 1"

    CadInputQueue.SendKeyin "OF=""E_Terrain_Slope"";SELVIEW 1"

    CadInputQueue.SendKeyin "OF=""E_Terrain_Rock"";SELVIEW 1"

    CadInputQueue.SendKeyin "OF=""E_Terrain_Ridgeline"";SELVIEW 1"

    CadInputQueue.SendKeyin "OF=""E_Terrain_Random"";SELVIEW 1"

    CadInputQueue.SendKeyin "OF=""E_Terrain_Pond"";SELVIEW 1"

    CadInputQueue.SendKeyin "OF=""E_Terrain_Points_Low"";SELVIEW 1"

    CadInputQueue.SendKeyin "OF=""E_Terrain_Points_High"";SELVIEW 1"

    CadInputQueue.SendKeyin "OF=""E_Terrain_Island"";SELVIEW 1"

    CadInputQueue.SendKeyin "OF=""E_Terrain_Interior"";SELVIEW 1"

    CadInputQueue.SendKeyin "OF=""E_Terrain_Hole"";SELVIEW 1"

    CadInputQueue.SendKeyin "OF=""E_Terrain_Flowline"";SELVIEW 1"

    CadInputQueue.SendKeyin "OF=""E_Terrain_Flow_Arrows"";SELVIEW 1"

    CadInputQueue.SendKeyin "OF=""E_Terrain_Fence"";SELVIEW 1"

    CadInputQueue.SendKeyin "OF=""E_Terrain_Exterior"";SELVIEW 1"

    CadInputQueue.SendKeyin "OF=""E_Terrain_DitchTop"";SELVIEW 1"

    CadInputQueue.SendKeyin "OF=""E_Terrain_DitchBottomFront"";SELVIEW 1"

    CadInputQueue.SendKeyin "OF=""E_Terrain_DitchBottomBack"";SELVIEW 1"

    CadInputQueue.SendKeyin "OF=""E_Terrain_Contours"";SELVIEW 1"

    CadInputQueue.SendKeyin "OF=""E_Terrain_Contour_Minor"";SELVIEW 1"

    CadInputQueue.SendKeyin "OF=""E_Terrain_Contour_Major"";SELVIEW 1"

    CadInputQueue.SendKeyin "OF=""E_Terrain_Contour_Label"";SELVIEW 1"

    CadInputQueue.SendKeyin "OF=""E_Terrain_Contour_Imported"";SELVIEW 1"

    CadInputQueue.SendKeyin "OF=""E_Terrain_Breakline"";SELVIEW 1"

    CadInputQueue.SendKeyin "OF=""E_Terrain_BoreHole"";SELVIEW 1"

    CadInputQueue.SendKeyin "OF=""E_Terrain_Bank"";SELVIEW 1"

    CadInputQueue.SendKeyin "OF=""E_Terrain"";SELVIEW 1"

    CadInputQueue.SendKeyin "OF=""E_ROW_PropertyLine"";SELVIEW 1"

    CadInputQueue.SendKeyin "OF=""E_ROW"";SELVIEW 1"

    CadInputQueue.SendKeyin "OF=""DTM_X_VOID"";SELVIEW 1"

    CadInputQueue.SendKeyin "OF=""DTM_X_UNSUITABLE_MATERIAL"";SELVIEW 1"

    CadInputQueue.SendKeyin "OF=""DTM_X_UNCLASS"";SELVIEW 1"

    CadInputQueue.SendKeyin "OF=""DTM_X_MUCK"";SELVIEW 1"

    CadInputQueue.SendKeyin "OF=""DTM_X_MOWING"";SELVIEW 1"

    CadInputQueue.SendKeyin "OF=""DTM_X_MERGE_3"";SELVIEW 1"

    CadInputQueue.SendKeyin "OF=""DTM_X_MERGE_2"";SELVIEW 1"

    CadInputQueue.SendKeyin "OF=""DTM_X_MERGE_1"";SELVIEW 1"

    CadInputQueue.SendKeyin "OF=""DTM_X_GROUND"";SELVIEW 1"

    CadInputQueue.SendKeyin "OF=""DTM_X_GRASSING"";SELVIEW 1"

    CadInputQueue.SendKeyin "OF=""DTM_X_FLOW_ARROWS"";SELVIEW 1"

    CadInputQueue.SendKeyin "OF=""DTM_X_FINAL"";SELVIEW 1"

    CadInputQueue.SendKeyin "OF=""DTM_X_EXCESS"";SELVIEW 1"

    CadInputQueue.SendKeyin "OF=""DTM_X_EXCAVATE_BOUNDARY"";SELVIEW 1"

    CadInputQueue.SendKeyin "OF=""DTM_X_EXCAVATE"";SELVIEW 1"

    CadInputQueue.SendKeyin "OF=""DTM_X_CONTOURS_MINOR_TX"";SELVIEW 1"

    CadInputQueue.SendKeyin "OF=""DTM_X_CONTOURS_MINOR"";SELVIEW 1"

    CadInputQueue.SendKeyin "OF=""DTM_X_CONTOURS_MAJOR_TX"";SELVIEW 1"

    CadInputQueue.SendKeyin "OF=""DTM_X_CONTOURS_MAJOR"";SELVIEW 1"

    CadInputQueue.SendKeyin "OF=""DTM_X_CONTOURS_ELEV_TX"";SELVIEW 1"

    CadInputQueue.SendKeyin "OF=""DTM_X_CLEARING"";SELVIEW 1"

    CadInputQueue.SendKeyin "OF=""DTM_X_BRIDGE"";SELVIEW 1"

    CadInputQueue.SendKeyin "OF=""DTM_X_BOUNDARY"";SELVIEW 1"

    CadInputQueue.SendKeyin "OF=""DTM_X_BORROW"";SELVIEW 1"

    CadInputQueue.SendKeyin "OF=""DTM_X_ADD"";SELVIEW 1"

    CadInputQueue.SendKeyin "OF=""DTM_TEMP_DROP_TRANS"";SELVIEW 1"

    CadInputQueue.SendKeyin "OF=""DTM_TEMP_DROP_STA"";SELVIEW 1"

    CadInputQueue.SendKeyin "OF=""DTM_TEMP_DROP"";SELVIEW 1"

    CadInputQueue.SendKeyin "OF=""DTM_SUPERELEVATION"";SELVIEW 1"

    CadInputQueue.SendKeyin "OF=""DTM_PNT_CTRL"";SELVIEW 1"

    CadInputQueue.SendKeyin "OF=""DTM_P_UNDERCUT"";SELVIEW 1"

    CadInputQueue.SendKeyin "OF=""DTM_P_SUBGRADE_2"";SELVIEW 1"

    CadInputQueue.SendKeyin "OF=""DTM_P_SUBGRADE_1"";SELVIEW 1"

    CadInputQueue.SendKeyin "OF=""DTM_P_SUBGRADE"";SELVIEW 1"

    CadInputQueue.SendKeyin "OF=""DTM_P_REMOVAL_BOUNDARY"";SELVIEW 1"

    CadInputQueue.SendKeyin "OF=""DTM_P_REMOVAL"";SELVIEW 1"

    CadInputQueue.SendKeyin "OF=""DTM_P_FINISHED_GRADE2"";SELVIEW 1"

    CadInputQueue.SendKeyin "OF=""DTM_P_FINISHED_GRADE1"";SELVIEW 1"

    CadInputQueue.SendKeyin "OF=""DTM_P_FINISHED_GRADE"";SELVIEW 1"

    CadInputQueue.SendKeyin "OF=""DTM_P_BRIDGE"";SELVIEW 1"

    CadInputQueue.SendKeyin "OF=""DTM_P_BOUNDARY"";SELVIEW 1"

    CadInputQueue.SendKeyin "OF=""DTM_DRAINAGE_CONTOURS"";SELVIEW 1"

    CadInputQueue.SendKeyin "OF=""DTM_CORRIDOR"";SELVIEW 1"

    CadInputQueue.SendKeyin "OF=""DTM_CONTOURS_MINOR_TX"";SELVIEW 1"

    CadInputQueue.SendKeyin "OF=""DTM_CONTOURS_MINOR"";SELVIEW 1"

    CadInputQueue.SendKeyin "OF=""DTM_CONTOURS_ELEV_TX"";SELVIEW 1"

    CadInputQueue.SendKeyin "OF=""DTM CONTOURS_MAJOR_TX"";SELVIEW 1"

    CadInputQueue.SendKeyin "OF=""DTM CONTOURS_MAJOR"";SELVIEW 1"

    CadInputQueue.SendKeyin "OF=""DRAINAGE_UNDERDRAINS"";SELVIEW 1"

    CadInputQueue.SendKeyin "OF=""DRAINAGE_TX"";SELVIEW 1"

    CadInputQueue.SendKeyin "OF=""DRAINAGE_SPUR_DIKES"";SELVIEW 1"

    CadInputQueue.SendKeyin "OF=""DRAINAGE_POND"";SELVIEW 1"

    CadInputQueue.SendKeyin "OF=""DRAINAGE_PIPES_CONC"";SELVIEW 1"

    CadInputQueue.SendKeyin "OF=""DRAINAGE_PIPES_ALT"";SELVIEW 1"

    CadInputQueue.SendKeyin "OF=""DRAINAGE_MANHOLES"";SELVIEW 1"

    CadInputQueue.SendKeyin "OF=""DRAINAGE_LAND_USE"";SELVIEW 1"

    CadInputQueue.SendKeyin "OF=""DRAINAGE_INLETS"";SELVIEW 1"

    CadInputQueue.SendKeyin "OF=""DRAINAGE_HGL"";SELVIEW 1"

    CadInputQueue.SendKeyin "OF=""DRAINAGE_GUTTER"";SELVIEW 1"

    CadInputQueue.SendKeyin "OF=""DRAINAGE_FLUMES"";SELVIEW 1"

    CadInputQueue.SendKeyin "OF=""DRAINAGE_FLOW_LINE_WRK"";SELVIEW 1"

    CadInputQueue.SendKeyin "OF=""DRAINAGE_FLOW_LINE"";SELVIEW 1"

    CadInputQueue.SendKeyin "OF=""DRAINAGE_FLOW_DIRECTION"";SELVIEW 1"

    CadInputQueue.SendKeyin "OF=""DRAINAGE_FLARED_END_SECTIONS"";SELVIEW 1"

    CadInputQueue.SendKeyin "OF=""DRAINAGE_EROSION_CTRL_SUPER_SILT_FENCE"";SELVIEW 1"

    CadInputQueue.SendKeyin "OF=""DRAINAGE_EROSION_CTRL_SOLID_SOD_DITCH"";SELVIEW 1"

    CadInputQueue.SendKeyin "OF=""DRAINAGE_EROSION_CTRL_SOIL_REINF_MATERIAL"";SELVIEW 1"

    CadInputQueue.SendKeyin "OF=""DRAINAGE_EROSION_CTRL_SILT_FENCE"";SELVIEW 1"

    CadInputQueue.SendKeyin "OF=""DRAINAGE_EROSION_CTRL_SILT_BASINS"";SELVIEW 1"

    CadInputQueue.SendKeyin "OF=""DRAINAGE_EROSION_CTRL_RIP_RAP_DITCH"";SELVIEW 1"

    CadInputQueue.SendKeyin "OF=""DRAINAGE_EROSION_CTRL_RIP_RAP_AREA"";SELVIEW 1"

    CadInputQueue.SendKeyin "OF=""DRAINAGE_EROSION_CTRL_PAVED_DITCH"";SELVIEW 1"

    CadInputQueue.SendKeyin "OF=""DRAINAGE_EROSION_CTRL_DITCH_LINER"";SELVIEW 1"

    CadInputQueue.SendKeyin "OF=""DRAINAGE_EROSION_CTRL_CHECKS"";SELVIEW 1"

    CadInputQueue.SendKeyin "OF=""DRAINAGE_EROSION_CTRL_BITUM_ROVING"";SELVIEW 1"

    CadInputQueue.SendKeyin "OF=""DRAINAGE_ENDWALLS"";SELVIEW 1"

    CadInputQueue.SendKeyin "OF=""DRAINAGE_EGL"";SELVIEW 1"

    CadInputQueue.SendKeyin "OF=""DRAINAGE_DRAFT"";SELVIEW 1"

    CadInputQueue.SendKeyin "OF=""DRAINAGE_DITCH_PLUGS"";SELVIEW 1"

    CadInputQueue.SendKeyin "OF=""DRAINAGE_CHANNEL_BOTTOM"";SELVIEW 1"

    CadInputQueue.SendKeyin "OF=""DRAINAGE_BOX_CULV"";SELVIEW 1"

    CadInputQueue.SendKeyin "OF=""DRAINAGE_AREA"";SELVIEW 1"

    CadInputQueue.SendKeyin "OF=""DRAINAGE_APRONS"";SELVIEW 1"

    CadInputQueue.SendKeyin "OF=""Drain_Trace"";SELVIEW 1"

    CadInputQueue.SendKeyin "OF=""Drain_Struc_Galvanized_Steel"";SELVIEW 1"

    CadInputQueue.SendKeyin "OF=""Drain_Struc_Concrete"";SELVIEW 1"

    CadInputQueue.SendKeyin "OF=""Drain_Struc_Cast_Iron"";SELVIEW 1"

    CadInputQueue.SendKeyin "OF=""Drain_Struc"";SELVIEW 1"

    CadInputQueue.SendKeyin "OF=""Drain_Pond"";SELVIEW 1"

    CadInputQueue.SendKeyin "OF=""Drain_Low Point"";SELVIEW 1"

    CadInputQueue.SendKeyin "OF=""Drain_Grade_Fixed_Tie"";SELVIEW 1"

    CadInputQueue.SendKeyin "OF=""Drain_Aquaplaning Surface"";SELVIEW 1"

    CadInputQueue.SendKeyin "OF=""Drain_Aquaplaning Flowline"";SELVIEW 1"

    CadInputQueue.SendKeyin "OF=""Draft_XS_Volume"";SELVIEW 1"

    CadInputQueue.SendKeyin "OF=""Draft_XS_Text"";SELVIEW 1"

    CadInputQueue.SendKeyin "OF=""Draft_XS_Sheet_Minor_Grid"";SELVIEW 1"

    CadInputQueue.SendKeyin "OF=""Draft_XS_Sheet_Major_Grid"";SELVIEW 1"

    CadInputQueue.SendKeyin "OF=""Draft_XS_Sheet_Border"";SELVIEW 1"

    CadInputQueue.SendKeyin "OF=""Draft_XS_Sheet_Annotation"";SELVIEW 1"

    CadInputQueue.SendKeyin "OF=""Draft_XS_Segment_Text"";SELVIEW 1"

    CadInputQueue.SendKeyin "OF=""Draft_XS_P_ROW_Lines"";SELVIEW 1"

    CadInputQueue.SendKeyin "OF=""Draft_XS_P_ROW_Labels"";SELVIEW 1"

    CadInputQueue.SendKeyin "OF=""Draft_XS_Labels"";SELVIEW 1"

    CadInputQueue.SendKeyin "OF=""Draft_XS_Grid"";SELVIEW 1"

    CadInputQueue.SendKeyin "OF=""Draft_XS_Feature_Text"";SELVIEW 1"

    CadInputQueue.SendKeyin "OF=""Draft_XS_E_ROW_Lines"";SELVIEW 1"

    CadInputQueue.SendKeyin "OF=""Draft_XS_E_ROW_Labels"";SELVIEW 1"

    CadInputQueue.SendKeyin "OF=""Draft_XS_Dynamic_View_Labels"";SELVIEW 1"

    CadInputQueue.SendKeyin "OF=""Draft_Survey_Civil_Labels"";SELVIEW 1"

    CadInputQueue.SendKeyin "OF=""Draft_Survey Water Label"";SELVIEW 1"

    CadInputQueue.SendKeyin "OF=""Draft_Survey Topo Label"";SELVIEW 1"

    CadInputQueue.SendKeyin "OF=""Draft_Survey Point Name"";SELVIEW 1"

    CadInputQueue.SendKeyin "OF=""Draft_Survey Point Elevation"";SELVIEW 1"

    CadInputQueue.SendKeyin "OF=""Draft_Survey Point Description"";SELVIEW 1"

    CadInputQueue.SendKeyin "OF=""Draft_Survey Field Code"";SELVIEW 1"

    CadInputQueue.SendKeyin "OF=""Draft_Survey Control Label"";SELVIEW 1"

    CadInputQueue.SendKeyin "OF=""Draft_Station_Labels"";SELVIEW 1"

    CadInputQueue.SendKeyin "OF=""Draft_Station Ticks Minor"";SELVIEW 1"

    CadInputQueue.SendKeyin "OF=""Draft_Station Ticks Major"";SELVIEW 1"

    CadInputQueue.SendKeyin "OF=""Draft_Station Labels Minor"";SELVIEW 1"

    CadInputQueue.SendKeyin "OF=""Draft_Station Labels Major"";SELVIEW 1"

    CadInputQueue.SendKeyin "OF=""Draft_Station Cardinal Points"";SELVIEW 1"

    CadInputQueue.SendKeyin "OF=""Draft_Station Cardinal Lines"";SELVIEW 1"

    CadInputQueue.SendKeyin "OF=""Draft_Spiral Data Label"";SELVIEW 1"

    CadInputQueue.SendKeyin "OF=""Draft_Slope_Labels"";SELVIEW 1"

    CadInputQueue.SendKeyin "OF=""Draft_Profile_Text"";SELVIEW 1"

    CadInputQueue.SendKeyin "OF=""Draft_Profile_Sheet_Minor_Grid"";SELVIEW 1"

    CadInputQueue.SendKeyin "OF=""Draft_Profile_Sheet_Major_Grid"";SELVIEW 1"

    CadInputQueue.SendKeyin "OF=""Draft_Profile_LP_HP_Text"";SELVIEW 1"

    CadInputQueue.SendKeyin "OF=""Draft_Profile_Labels"";SELVIEW 1"

    CadInputQueue.SendKeyin "OF=""Draft_Profile_Grid"";SELVIEW 1"

    CadInputQueue.SendKeyin "OF=""Draft_Plan_Labels"";SELVIEW 1"

    CadInputQueue.SendKeyin "OF=""Draft_Elevation_Labels"";SELVIEW 1"

    CadInputQueue.SendKeyin "OF=""Draft_Curve Data Label"";SELVIEW 1"

    CadInputQueue.SendKeyin "OF=""Draft_Corr_Transition_Final"";SELVIEW 1"

    CadInputQueue.SendKeyin "OF=""Draft_Corr_Transition_Design"";SELVIEW 1"

    CadInputQueue.SendKeyin "OF=""Draft_Corr_Transition_Conceptual"";SELVIEW 1"

    CadInputQueue.SendKeyin "OF=""Draft_Corr_TemplateDrop_Final"";SELVIEW 1"

    CadInputQueue.SendKeyin "OF=""Draft_Corr_TemplateDrop_Design"";SELVIEW 1"

    CadInputQueue.SendKeyin "OF=""Draft_Corr_TemplateDrop_Conceptual"";SELVIEW 1"

    CadInputQueue.SendKeyin "OF=""Draft_Corr_Superelevation Right Lane"";SELVIEW 1"

    CadInputQueue.SendKeyin "OF=""Draft_Corr_Superelevation Left Lane"";SELVIEW 1"

    CadInputQueue.SendKeyin "OF=""Draft_Corr_Superelevation"";SELVIEW 1"

    CadInputQueue.SendKeyin "OF=""Draft_Corr_Secondary Alignment"";SELVIEW 1"

    CadInputQueue.SendKeyin "OF=""Draft_Corr_Range_Final"";SELVIEW 1"

    CadInputQueue.SendKeyin "OF=""Draft_Corr_Range_Design"";SELVIEW 1"

    CadInputQueue.SendKeyin "OF=""Draft_Corr_Range_Conceptual"";SELVIEW 1"

    CadInputQueue.SendKeyin "OF=""Draft_Corr_Point Control"";SELVIEW 1"

    CadInputQueue.SendKeyin "OF=""Draft_Corr_Key Station"";SELVIEW 1"

    CadInputQueue.SendKeyin "OF=""Draft_Corr_Final"";SELVIEW 1"

    CadInputQueue.SendKeyin "OF=""Draft_Corr_End Cond Exception"";SELVIEW 1"

    CadInputQueue.SendKeyin "OF=""Draft_Corr_Design"";SELVIEW 1"

    CadInputQueue.SendKeyin "OF=""Draft_Corr_Conceptual"";SELVIEW 1"

    CadInputQueue.SendKeyin "OF=""Draft_Coordinate_Labels"";SELVIEW 1"

    CadInputQueue.SendKeyin "OF=""Draft_Bearing Label"";SELVIEW 1"

    CadInputQueue.SendKeyin "OF=""Draft_Alignment_Labels"";SELVIEW 1"

    CadInputQueue.SendKeyin "OF=""Constructions"";SELVIEW 1"

    CadInputQueue.SendKeyin "OF=""CONST_PROF_LV3"";SELVIEW 1"

    CadInputQueue.SendKeyin "OF=""CONST_PROF_LV2"";SELVIEW 1"

    CadInputQueue.SendKeyin "OF=""CONST_PROF_LV1"";SELVIEW 1"

    CadInputQueue.SendKeyin "OF=""CONST_LV10"";SELVIEW 1"

    CadInputQueue.SendKeyin "OF=""CONST_LV9"";SELVIEW 1"

    CadInputQueue.SendKeyin "OF=""CONST_LV8"";SELVIEW 1"

    CadInputQueue.SendKeyin "OF=""CONST_LV7"";SELVIEW 1"

    CadInputQueue.SendKeyin "OF=""CONST_LV6"";SELVIEW 1"

    CadInputQueue.SendKeyin "OF=""CONST_LV5"";SELVIEW 1"

    CadInputQueue.SendKeyin "OF=""CONST_LV4"";SELVIEW 1"

    CadInputQueue.SendKeyin "OF=""CONST_LV3"";SELVIEW 1"

    CadInputQueue.SendKeyin "OF=""CONST_LV2"";SELVIEW 1"

    CadInputQueue.SendKeyin "OF=""CONST_LV1"";SELVIEW 1"

    CadInputQueue.SendKeyin "OF=""CONST_DCH"";SELVIEW 1"

    CadInputQueue.SendKeyin "OF=""Clipping_Shape"";SELVIEW 1"

    CadInputQueue.SendKeyin "OF=""Cable Barrier"";SELVIEW 1"

    CadInputQueue.SendKeyin "OF=""BRD_XS_X_Ground"";SELVIEW 1"

    CadInputQueue.SendKeyin "OF=""BRD_X_Boundary"";SELVIEW 1"

    CadInputQueue.SendKeyin "OF=""BRD_Terrain_X_Ground"";SELVIEW 1"

    CadInputQueue.SendKeyin "OF=""BRD_Table_Text"";SELVIEW 1"

    CadInputQueue.SendKeyin "OF=""BRD_Table_Lines"";SELVIEW 1"

    CadInputQueue.SendKeyin "OF=""BRD_STL"";SELVIEW 1"

    CadInputQueue.SendKeyin "OF=""BRD_Stamp"";SELVIEW 1"

    CadInputQueue.SendKeyin "OF=""BRD_Slope"";SELVIEW 1"

    CadInputQueue.SendKeyin "OF=""BRD_ScourLine"";SELVIEW 1"

    CadInputQueue.SendKeyin "OF=""BRD_Riprap"";SELVIEW 1"

    CadInputQueue.SendKeyin "OF=""BRD_Rebar_Warnings"";SELVIEW 1"

    CadInputQueue.SendKeyin "OF=""BRD_Rebar_Labels"";SELVIEW 1"

    CadInputQueue.SendKeyin "OF=""BRD_Rebar_Hatching"";SELVIEW 1"

    CadInputQueue.SendKeyin "OF=""BRD_Railing_Steel"";SELVIEW 1"

    CadInputQueue.SendKeyin "OF=""BRD_Railing_Concrete"";SELVIEW 1"

    CadInputQueue.SendKeyin "OF=""BRD_Pile_Concrete"";SELVIEW 1"

    CadInputQueue.SendKeyin "OF=""BRD_NotForConstruction"";SELVIEW 1"

    CadInputQueue.SendKeyin "OF=""BRD_Notes_Title"";SELVIEW 1"

    CadInputQueue.SendKeyin "OF=""BRD_Notes_Body"";SELVIEW 1"

    CadInputQueue.SendKeyin "OF=""BRD_NOTES"";SELVIEW 1"

    CadInputQueue.SendKeyin "OF=""BRD_Misc_Rebar"";SELVIEW 1"

    CadInputQueue.SendKeyin "OF=""BRD_HIDN_STL"";SELVIEW 1"

    CadInputQueue.SendKeyin "OF=""BRD_HIDN_PILE"";SELVIEW 1"

    CadInputQueue.SendKeyin "OF=""BRD_HIDN_CONC"";SELVIEW 1"

    CadInputQueue.SendKeyin "OF=""BRD_HIDN"";SELVIEW 1"

    CadInputQueue.SendKeyin "OF=""BRD_GroundLine"";SELVIEW 1"

    CadInputQueue.SendKeyin "OF=""BRD_Footing_Rebar"";SELVIEW 1"

    CadInputQueue.SendKeyin "OF=""BRD_Footing_Concrete"";SELVIEW 1"

    CadInputQueue.SendKeyin "OF=""BRD_FNSH_GRDE"";SELVIEW 1"

    CadInputQueue.SendKeyin "OF=""BRD_EndWall_Rebar"";SELVIEW 1"

    CadInputQueue.SendKeyin "OF=""BRD_EndWall_Concrete"";SELVIEW 1"

    CadInputQueue.SendKeyin "OF=""BRD_DrilledShaft_Rebar"";SELVIEW 1"

    CadInputQueue.SendKeyin "OF=""BRD_DrilledShaft_Concrete"";SELVIEW 1"

    CadInputQueue.SendKeyin "OF=""BRD_Dimension_Text"";SELVIEW 1"

    CadInputQueue.SendKeyin "OF=""BRD_Dimension_Lines"";SELVIEW 1"

    CadInputQueue.SendKeyin "OF=""BRD_DIM"";SELVIEW 1"

    CadInputQueue.SendKeyin "OF=""BRD_Diaphragm_Concrete"";SELVIEW 1"

    CadInputQueue.SendKeyin "OF=""BRD_Deck_Rebar"";SELVIEW 1"

    CadInputQueue.SendKeyin "OF=""BRD_Deck_Concrete"";SELVIEW 1"

    CadInputQueue.SendKeyin "OF=""BRD_CrossFrames"";SELVIEW 1"

    CadInputQueue.SendKeyin "OF=""BRD_CrashBarrier"";SELVIEW 1"

    CadInputQueue.SendKeyin "OF=""BRD_Contours_Minor_TX"";SELVIEW 1"

    CadInputQueue.SendKeyin "OF=""BRD_Contours_Minor"";SELVIEW 1"

    CadInputQueue.SendKeyin "OF=""BRD_Concrete_Misc"";SELVIEW 1"

    CadInputQueue.SendKeyin "OF=""BRD_Comments_Orange"";SELVIEW 1"

    CadInputQueue.SendKeyin "OF=""BRD_Comments_Blue"";SELVIEW 1"

    CadInputQueue.SendKeyin "OF=""BRD_Column_Tie"";SELVIEW 1"

    CadInputQueue.SendKeyin "OF=""BRD_Column_Stirrups"";SELVIEW 1"

    CadInputQueue.SendKeyin "OF=""BRD_Column_Rebar"";SELVIEW 1"

    CadInputQueue.SendKeyin "OF=""BRD_Column_Concrete"";SELVIEW 1"

    CadInputQueue.SendKeyin "OF=""BRD_CL"";SELVIEW 1"

    CadInputQueue.SendKeyin "OF=""BRD_Cap_Stirrups"";SELVIEW 1"

    CadInputQueue.SendKeyin "OF=""BRD_Cap_Rebar"";SELVIEW 1"

    CadInputQueue.SendKeyin "OF=""BRD_Cap_Concrete"";SELVIEW 1"

    CadInputQueue.SendKeyin "OF=""BRD_Bearing"";SELVIEW 1"

    CadInputQueue.SendKeyin "OF=""BRD_Beam_Tendons"";SELVIEW 1"

    CadInputQueue.SendKeyin "OF=""BRD_Beam_Strands"";SELVIEW 1"

    CadInputQueue.SendKeyin "OF=""BRD_Beam_Stirrups"";SELVIEW 1"

    CadInputQueue.SendKeyin "OF=""BRD_Beam_Steel"";SELVIEW 1"

    CadInputQueue.SendKeyin "OF=""BRD_Beam_Concrete"";SELVIEW 1"

    CadInputQueue.SendKeyin "OF=""BRD_Abutment_Rebar"";SELVIEW 1"

    CadInputQueue.SendKeyin "OF=""BRD_Abutment_Concrete"";SELVIEW 1"

    CadInputQueue.SendKeyin "OF=""BRD_ Contours_Major_TX"";SELVIEW 1"

    CadInputQueue.SendKeyin "OF=""BRD_ Contours_Major"";SELVIEW 1"

    CadInputQueue.SendKeyin "OF=""ASPHALT_OGFC"";SELVIEW 1"

    CadInputQueue.SendKeyin "OF=""ASPHALT_25MM2"";SELVIEW 1"

    CadInputQueue.SendKeyin "OF=""ASPHALT_25MM1"";SELVIEW 1"

    CadInputQueue.SendKeyin "OF=""ASPHALT_19MM2"";SELVIEW 1"

    CadInputQueue.SendKeyin "OF=""ASPHALT_19MM1"";SELVIEW 1"

    CadInputQueue.SendKeyin "OF=""ASPHALT_9_5MM1"";SELVIEW 1"

    CadInputQueue.SendKeyin "OF=""ASHPALT_12_5MM2"";SELVIEW 1"

    CadInputQueue.SendKeyin "OF=""ASHPALT_12_5MM1"";SELVIEW 1"

    CadInputQueue.SendKeyin "OF=""ASHPALT_9_5MM2"";SELVIEW 1"

    CadInputQueue.SendKeyin "OF=""ALI_DESIGN_SECONDARY_TICS_SMALL"";SELVIEW 1"

    CadInputQueue.SendKeyin "OF=""ALI_DESIGN_SECONDARY_TICS"";SELVIEW 1"

    CadInputQueue.SendKeyin "OF=""ALI_DESIGN_SECONDARY_STA_SMALL"";SELVIEW 1"

    CadInputQueue.SendKeyin "OF=""ALI_DESIGN_SECONDARY_STA"";SELVIEW 1"

    CadInputQueue.SendKeyin "OF=""ALI_DESIGN_SECONDARY_LABELS_TX"";SELVIEW 1"

    CadInputQueue.SendKeyin "OF=""ALI_DESIGN_SECONDARY_LABELS"";SELVIEW 1"

    CadInputQueue.SendKeyin "OF=""ALI_DESIGN_SECONDARY_CURVES"";SELVIEW 1"

    CadInputQueue.SendKeyin "OF=""ALI_DESIGN_SECONDARY_CURVE_DATA"";SELVIEW 1"

    CadInputQueue.SendKeyin "OF=""ALI_DESIGN_SECONDARY"";SELVIEW 1"

    CadInputQueue.SendKeyin "OF=""ALI_DESIGN_ML_TICS_SMALL"";SELVIEW 1"

    CadInputQueue.SendKeyin "OF=""ALI_DESIGN_ML_TICS"";SELVIEW 1"

    CadInputQueue.SendKeyin "OF=""ALI_DESIGN_ML_STA_SMALL"";SELVIEW 1"

    CadInputQueue.SendKeyin "OF=""ALI_DESIGN_ML_STA"";SELVIEW 1"

    CadInputQueue.SendKeyin "OF=""ALI_DESIGN_ML_LABELS_TX"";SELVIEW 1"

    CadInputQueue.SendKeyin "OF=""ALI_DESIGN_ML_LABELS"";SELVIEW 1"

    CadInputQueue.SendKeyin "OF=""ALI_DESIGN_ML_CURVES"";SELVIEW 1"

    CadInputQueue.SendKeyin "OF=""ALI_DESIGN_ML_CURVE_DATA"";SELVIEW 1"

    CadInputQueue.SendKeyin "OF=""ALI_DESIGN_ML_ALT3_TICS_SMALL"";SELVIEW 1"

    CadInputQueue.SendKeyin "OF=""ALI_DESIGN_ML_ALT3_TICS"";SELVIEW 1"

    CadInputQueue.SendKeyin "OF=""ALI_DESIGN_ML_ALT3_STA_SMALL"";SELVIEW 1"

    CadInputQueue.SendKeyin "OF=""ALI_DESIGN_ML_ALT3_STA"";SELVIEW 1"

    CadInputQueue.SendKeyin "OF=""ALI_DESIGN_ML_ALT3_LABELS_TX"";SELVIEW 1"

    CadInputQueue.SendKeyin "OF=""ALI_DESIGN_ML_ALT3_LABELS"";SELVIEW 1"

    CadInputQueue.SendKeyin "OF=""ALI_DESIGN_ML_ALT3_CURVE_DATA"";SELVIEW 1"

    CadInputQueue.SendKeyin "OF=""ALI_DESIGN_ML_ALT3"";SELVIEW 1"

    CadInputQueue.SendKeyin "OF=""ALI_DESIGN_ML_ALT2_TICS_SMALL"";SELVIEW 1"

    CadInputQueue.SendKeyin "OF=""ALI_DESIGN_ML_ALT2_TICS"";SELVIEW 1"

    CadInputQueue.SendKeyin "OF=""ALI_DESIGN_ML_ALT2_STA_SMALL"";SELVIEW 1"

    CadInputQueue.SendKeyin "OF=""ALI_DESIGN_ML_ALT2_STA"";SELVIEW 1"

    CadInputQueue.SendKeyin "OF=""ALI_DESIGN_ML_ALT2_LABELS_TX"";SELVIEW 1"

    CadInputQueue.SendKeyin "OF=""ALI_DESIGN_ML_ALT2_LABELS"";SELVIEW 1"

    CadInputQueue.SendKeyin "OF=""ALI_DESIGN_ML_ALT2_CURVE_DATA"";SELVIEW 1"

    CadInputQueue.SendKeyin "OF=""ALI_DESIGN_ML_ALT2"";SELVIEW 1"

    CadInputQueue.SendKeyin "OF=""ALI_DESIGN_ML_ALT1_TICS_SMALL"";SELVIEW 1"

    CadInputQueue.SendKeyin "OF=""ALI_DESIGN_ML_ALT1_TICS"";SELVIEW 1"

    CadInputQueue.SendKeyin "OF=""ALI_DESIGN_ML_ALT1_STA_SMALL"";SELVIEW 1"

    CadInputQueue.SendKeyin "OF=""ALI_DESIGN_ML_ALT1_STA"";SELVIEW 1"

    CadInputQueue.SendKeyin "OF=""ALI_DESIGN_ML_ALT1_LABELS_TX"";SELVIEW 1"

    CadInputQueue.SendKeyin "OF=""ALI_DESIGN_ML_ALT1_LABELS"";SELVIEW 1"

    CadInputQueue.SendKeyin "OF=""ALI_DESIGN_ML_ALT1_CURVE_DATA"";SELVIEW 1"

    CadInputQueue.SendKeyin "OF=""ALI_DESIGN_ML_ALT1"";SELVIEW 1"

    CadInputQueue.SendKeyin "OF=""ALI_DESIGN_ML__ALT3_CURVES"";SELVIEW 1"

    CadInputQueue.SendKeyin "OF=""ALI_DESIGN_ML__ALT2_CURVES"";SELVIEW 1"

    CadInputQueue.SendKeyin "OF=""ALI_DESIGN_ML__ALT1_CURVES"";SELVIEW 1"

    CadInputQueue.SendKeyin "OF=""ALI_DESIGN_ML"";SELVIEW 1"

    CadInputQueue.SendKeyin "OF=""ALI_DESIGN_LR_TICS_SMALL"";SELVIEW 1"

    CadInputQueue.SendKeyin "OF=""ALI_DESIGN_LR_TICS"";SELVIEW 1"

    CadInputQueue.SendKeyin "OF=""ALI_DESIGN_LR_STA_SMALL"";SELVIEW 1"

    CadInputQueue.SendKeyin "OF=""ALI_DESIGN_LR_STA"";SELVIEW 1"

    CadInputQueue.SendKeyin "OF=""ALI_DESIGN_LR_LABELS_TX"";SELVIEW 1"

    CadInputQueue.SendKeyin "OF=""ALI_DESIGN_LR_LABELS"";SELVIEW 1"

    CadInputQueue.SendKeyin "OF=""ALI_DESIGN_LR_CURVES"";SELVIEW 1"

    CadInputQueue.SendKeyin "OF=""ALI_DESIGN_LR_CURVE_DATA"";SELVIEW 1"

    CadInputQueue.SendKeyin "OF=""ALI_DESIGN_LR"";SELVIEW 1"

    CadInputQueue.SendKeyin "OF=""ALI_DESIGN_DRAINAGE_TICS_SMALL"";SELVIEW 1"

    CadInputQueue.SendKeyin "OF=""ALI_DESIGN_DRAINAGE_TICS"";SELVIEW 1"

    CadInputQueue.SendKeyin "OF=""ALI_DESIGN_DRAINAGE_STA_SMALL"";SELVIEW 1"

    CadInputQueue.SendKeyin "OF=""ALI_DESIGN_DRAINAGE_STA"";SELVIEW 1"

    CadInputQueue.SendKeyin "OF=""ALI_DESIGN_DRAINAGE_LABELS_TX"";SELVIEW 1"

    CadInputQueue.SendKeyin "OF=""ALI_DESIGN_DRAINAGE_LABELS"";SELVIEW 1"

    CadInputQueue.SendKeyin "OF=""ALI_DESIGN_DRAINAGE_CURVE_DATA"";SELVIEW 1"

    CadInputQueue.SendKeyin "OF=""ALI_DESIGN_DRAINAGE"";SELVIEW 1"

    CadInputQueue.SendKeyin "OF=""ALI_DESIGN_DETOUR_TICS_SMALL"";SELVIEW 1"

    CadInputQueue.SendKeyin "OF=""ALI_DESIGN_DETOUR_TICS"";SELVIEW 1"

    CadInputQueue.SendKeyin "OF=""ALI_DESIGN_DETOUR_STA_SMALL"";SELVIEW 1"

    CadInputQueue.SendKeyin "OF=""ALI_DESIGN_DETOUR_STA"";SELVIEW 1"

    CadInputQueue.SendKeyin "OF=""ALI_DESIGN_DETOUR_LABELS_TX"";SELVIEW 1"

    CadInputQueue.SendKeyin "OF=""ALI_DESIGN_DETOUR_LABELS"";SELVIEW 1"

    CadInputQueue.SendKeyin "OF=""ALI_DESIGN_DETOUR_CURVES"";SELVIEW 1"

    CadInputQueue.SendKeyin "OF=""ALI_DESIGN_DETOUR_CURVE_DATA"";SELVIEW 1"

    CadInputQueue.SendKeyin "OF=""ALI_DESIGN_DETOUR"";SELVIEW 1"

    CadInputQueue.SendKeyin "OF=""Ali_Design_Baseline_Sta"";SELVIEW 1"

    CadInputQueue.SendKeyin "OF=""Ali_Design_Baseline_Curve_Data"";SELVIEW 1"

    CadInputQueue.SendKeyin "OF=""Ali_Design_Baseline"";SELVIEW 1"

    CadInputQueue.SendKeyin "OF=""ALI_DESIGN_AUX_TICS_SMALL"";SELVIEW 1"

    CadInputQueue.SendKeyin "OF=""ALI_DESIGN_AUX_TICS"";SELVIEW 1"

    CadInputQueue.SendKeyin "OF=""ALI_DESIGN_AUX_STA_SMALL"";SELVIEW 1"

    CadInputQueue.SendKeyin "OF=""ALI_DESIGN_AUX_STA"";SELVIEW 1"

    CadInputQueue.SendKeyin "OF=""ALI_DESIGN_AUX_LABELS_TX"";SELVIEW 1"

    CadInputQueue.SendKeyin "OF=""ALI_DESIGN_AUX_LABELS"";SELVIEW 1"

    CadInputQueue.SendKeyin "OF=""ALI_DESIGN_AUX_CURVES"";SELVIEW 1"

    CadInputQueue.SendKeyin "OF=""ALI_DESIGN_AUX_CURVE_DATA"";SELVIEW 1"

    CadInputQueue.SendKeyin "OF=""ALI_DESIGN_AUX"";SELVIEW 1"

    CadInputQueue.SendKeyin "OF=""17"";SELVIEW 1"

    CadInputQueue.SendKeyin "OF=""0"";SELVIEW 1"

    CadInputQueue.SendKeyin "OF=""XS_X_ADD"";SELVIEW 1"

    CadInputQueue.SendKeyin "OF=""XS_P_SUBGRADE_GRANULAR"";SELVIEW 1"

    CadInputQueue.SendKeyin "ON=""XS_P_SUBGRADE_GRANULAR"";SELVIEW 1"

    CadInputQueue.SendCommand "PLACE FENCE ICON"

    point.X = startPoint.X - 845.560411333432
    point.Y = startPoint.Y + 445.164897304962
    point.Z = startPoint.Z
    CadInputQueue.SendDataPoint point, 1

    point.X = startPoint.X + 1136.06604173625
    point.Y = startPoint.Y - 752.94451573698
    point.Z = startPoint.Z
    CadInputQueue.SendDataPoint point, 1

    CadInputQueue.SendCommand "FENCE DELETE"

    point.X = startPoint.X - 10.5948324422984
    point.Y = startPoint.Y + 180.598149945543
    point.Z = startPoint.Z
    CadInputQueue.SendDataPoint point, 1

    CadInputQueue.SendKeyin "ON=""Default"";SELVIEW 1"

    CadInputQueue.SendKeyin "ON=""XS_X_GROUND"";SELVIEW 1"

    CadInputQueue.SendKeyin "ON=""XS_SHEET_MINOR_GRIDS"";SELVIEW 1"

    CadInputQueue.SendKeyin "ON=""XS_SHEET_MEDIUM_GRIDS"";SELVIEW 1"

    CadInputQueue.SendKeyin "ON=""XS_SHEET_MAJOR_GRIDS"";SELVIEW 1"

    CadInputQueue.SendKeyin "ON=""XS_SHEET_LABELS_STATION"";SELVIEW 1"

    CadInputQueue.SendKeyin "ON=""XS_SHEET_LABELS_OFFSET"";SELVIEW 1"

    CadInputQueue.SendKeyin "ON=""XS_SHEET_LABELS_ELEVATION"";SELVIEW 1"

    CadInputQueue.SendKeyin "ON=""XS_P_TX_FS_BS"";SELVIEW 1"

    CadInputQueue.SendKeyin "ON=""SHEET_BORDER"";SELVIEW 1"

    CadInputQueue.SendKeyin "ON=""Draft_XS_Volume_Annotation"";SELVIEW 1"

    CadInputQueue.SendKeyin "ON=""Draft_Named_Boundary"";SELVIEW 1"

    CadInputQueue.SendKeyin "ON=""Draft_Civil_Labels"";SELVIEW 1"

    CadInputQueue.SendKeyin "ON=""XS_X_DRAINAGE"";SELVIEW 1"

    CadInputQueue.SendKeyin "ON=""XS_P_GROUND"";SELVIEW 1"

    CadInputQueue.SendKeyin "ON=""XS_P_FINISHED_GRADE_ELEV_TX"";SELVIEW 1"

    CadInputQueue.SendKeyin "ON=""XS_P_DRAINAGE"";SELVIEW 1"

    CadInputQueue.SendKeyin "ON=""XS_P_DR_ASPHALT"";SELVIEW 1"

    CadInputQueue.SendKeyin "ON=""X_ROW"";SELVIEW 1"

    CadInputQueue.SendKeyin "ON=""X_PROFILES_1"";SELVIEW 1"

    CadInputQueue.SendKeyin "ON=""SHEET_TITLE_BLOCK_TX"";SELVIEW 1"

    CadInputQueue.SendKeyin "ON=""SHEET_TITLE_BLOCK"";SELVIEW 1"

    CadInputQueue.SendKeyin "ON=""SHEET_PRELIM"";SELVIEW 1"

    CadInputQueue.SendKeyin "ON=""SHEET_PLOTTING_SHAPE"";SELVIEW 1"

    CadInputQueue.SendKeyin "ON=""SHEET_MDOT_LOGO"";SELVIEW 1"

    CadInputQueue.SendKeyin "ON=""SHEET_LOGO"";SELVIEW 1"

    CadInputQueue.SendKeyin "ON=""SHEET_CONSULTANT_STAMP"";SELVIEW 1"

    CadInputQueue.SendKeyin "ON=""ROW_LINES"";SELVIEW 1"

    point.X = startPoint.X + 176.42234473015
    point.Y = startPoint.Y - 191.685058838783
    point.Z = startPoint.Z
    CadInputQueue.SendDataPoint point, 1

    point.X = startPoint.X + 189.412121313211
    point.Y = startPoint.Y - 112.730489112574
    point.Z = startPoint.Z
    CadInputQueue.SendDataPoint point, 1

    CommandState.StartDefaultCommand
End Sub




'=====================================================
' WRAPPER
' Loops all models in the active DGN, but only runs
' on NON-sheet models whose station ends in +00 or +50.
'=====================================================
Public Sub XS_RunAction_AllXS_OnlyPlus00or50()

    'Collect model names first (safer than activating during enumeration)
    Dim modelNames As Collection
    Set modelNames = New Collection

    Dim mm As Object
    For Each mm In ActiveDesignFile.Models
        modelNames.Add mm.Name
    Next mm

    Dim processed As Long
    Dim skippedSheet As Long, skippedNoStation As Long, skippedNot00or50 As Long

    Dim nm As Variant
    For Each nm In modelNames

        Dim m As Object
        Set m = ActiveDesignFile.Models.Item(CStr(nm))

        If IsSheetModelName(CStr(m.Name)) Then
            skippedSheet = skippedSheet + 1
            GoTo ContinueModel
        End If

        Dim tok As String
        tok = ExtractStationToken(CStr(m.Name))

        If Len(tok) = 0 Then
            skippedNoStation = skippedNoStation + 1
            GoTo ContinueModel
        End If

        If Not StationTokenIsPlus00or50(tok, 0.0001) Then
            skippedNot00or50 = skippedNot00or50 + 1
            GoTo ContinueModel
        End If

        'Activate the XS model
        m.Activate

        'Run your recorded action / macro here
        RunXsAction

        processed = processed + 1

ContinueModel:
    Next nm

    CadInputQueue.SendCommand "FILEDESIGN SAVESETTINGS"

    MsgBox "Done." & vbCrLf & _
           "Processed (+00/+50): " & processed & vbCrLf & _
           "Skipped sheets: " & skippedSheet & vbCrLf & _
           "Skipped (no station token): " & skippedNoStation & vbCrLf & _
           "Skipped (not +00/+50): " & skippedNot00or50, vbInformation, "OpenRoads"

End Sub

'=== EDIT THIS ONLY ===
Private Sub RunXsAction()
    'Put YOUR sub call here, for example:
    Call BmrXs_Clean_up_2
    'Call BmrXs_Clean_up_2_all_Sheets
End Sub
'======================

Private Function IsSheetModelName(ByVal modelName As String) As Boolean
    'Most reliable in ORD: use the UI suffix you’re seeing
    IsSheetModelName = (InStr(1, modelName, "[Sheet]", vbTextCompare) > 0)
End Function

Private Function ExtractStationToken(ByVal modelName As String) As String
    On Error GoTo EH

    Dim re As Object
    Set re = CreateObject("VBScript.RegExp")
    re.Pattern = "(-?\d+\+\d+(?:\.\d+)?)"
    re.Global = False
    re.IgnoreCase = True

    If re.Test(modelName) Then
        ExtractStationToken = re.Execute(modelName)(0).SubMatches(0)
    Else
        ExtractStationToken = ""
    End If
    Exit Function

EH:
    ExtractStationToken = ""
End Function

'True only for tokens ending in +00 or +50 (minor part = 0 or 50 within tolerance)
Private Function StationTokenIsPlus00or50(ByVal stTok As String, ByVal tol As Double) As Boolean

    Dim s As String: s = Trim$(stTok)

    'Strip sign
    If Left$(s, 1) = "-" Or Left$(s, 1) = "+" Then s = Mid$(s, 2)

    Dim parts() As String
    parts = Split(s, "+")
    If UBound(parts) < 1 Then
        StationTokenIsPlus00or50 = False
        Exit Function
    End If

    Dim minor As Double
    minor = CDbl(parts(1))

    StationTokenIsPlus00or50 = (Abs(minor - 0#) <= tol Or Abs(minor - 50#) <= tol)

End Function
