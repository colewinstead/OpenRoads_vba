Attribute VB_Name = "USGSTerrainDownloaderMain"
Option Explicit

Private mModel As ModelReference
Private mPicker As clsTerrainBoundaryPicker
Private mBoundary As String
Private mOpen As Boolean
Private mUnitsContext As String
Private mGCSContext As String

Public Sub Main()

    If mOpen Then
        frmUSGSTerrainDownloader.Show vbModeless
        Exit Sub
    End If
    TerrainRequire ActiveModelReference.Type = msdModelTypeNormal, "Open an active design model, not a sheet or drawing model."
    Set mModel = ActiveModelReference
    mUnitsContext = TerrainModelDescription()
    mGCSContext = TerrainDetectedGCS()
    mBoundary = "": mOpen = True
    frmUSGSTerrainDownloader.Show vbModeless
    Exit Sub
Failed:
    MsgBox Err.Description, vbExclamation, "USGS Terrain Downloader"
End Sub

Public Sub TerrainRequire(ByVal condition As Boolean, ByVal message As String)
    If Not condition Then Err.Raise vbObjectError + 2801, "USGS Terrain Downloader", message
End Sub

Public Sub TerrainCheckContext(Optional ByVal checkGCS As Boolean = False)
    TerrainRequire mOpen And Not mModel Is Nothing, "Start the terrain downloader again."
    TerrainRequire mModel.IsActive, "The active model changed. Close this dialog and start again in the intended model."
    TerrainRequire TerrainModelDescription() = mUnitsContext, "Model working units changed. Close the dialog and select the boundary again."
    If checkGCS Then TerrainRequire TerrainDetectedGCS() = mGCSContext, "Model GCS changed. Close the dialog and verify the new coordinate mapping."
End Sub

Public Function TerrainBoundaryJSON() As String
    TerrainCheckContext
    TerrainRequire Len(mBoundary) > 0, "Draw a rectangle or select a closed straight-sided shape first."
    TerrainBoundaryJSON = mBoundary
End Function

Public Sub TerrainPick(ByVal rectangle As Boolean)
    On Error GoTo Failed
    TerrainCheckContext
    Set mPicker = New clsTerrainBoundaryPicker
    frmUSGSTerrainDownloader.Hide
    If rectangle Then
        CommandState.StartPrimitive mPicker
    Else
        CommandState.StartLocate mPicker
    End If
    Exit Sub
Failed:
    MsgBox Err.Description, vbExclamation, "Boundary selection"
    frmUSGSTerrainDownloader.Show vbModeless
End Sub

Public Sub TerrainAcceptBoundary(vertices() As Point3d)
    TerrainCheckContext
    mBoundary = TerrainVerticesJSON(vertices)
    frmUSGSTerrainDownloader.BoundaryChanged "Boundary captured: " & CStr(UBound(vertices) - LBound(vertices) + 1) & " vertices in model XY master units. Search calculates geographic extent."
End Sub

Public Sub TerrainPickerEnded()
    Set mPicker = Nothing
    If mOpen Then frmUSGSTerrainDownloader.Show vbModeless
End Sub

Public Sub TerrainClose()
    mOpen = False
    If Not mPicker Is Nothing Then mPicker.StopPick
    Set mPicker = Nothing
    Set mModel = Nothing
    mBoundary = ""
End Sub

Attribute VB_Name = "clsTerrainBoundaryPicker"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
Implements IPrimitiveCommandEvents
Implements ILocateCommandEvents

Private mFirst As Point3d
Private mHaveFirst As Boolean
Private mFinishing As Boolean

Private Sub RectangleVertices(last As Point3d, vertices() As Point3d)
    ReDim vertices(0 To 4)
    vertices(0) = mFirst
    vertices(1) = Point3dFromXYZ(last.x, mFirst.y, mFirst.Z)
    vertices(2) = Point3dFromXYZ(last.x, last.y, mFirst.Z)
    vertices(3) = Point3dFromXYZ(mFirst.x, last.y, mFirst.Z)
    vertices(4) = mFirst
End Sub

Private Sub IPrimitiveCommandEvents_Start()
    ShowCommand "USGS Terrain Downloader - Rectangle"
    ShowPrompt "Pick first corner. Rectangle follows model XY, even in a rotated view. Reset cancels."
    CommandState.EnableAccuSnap
End Sub

Private Sub IPrimitiveCommandEvents_DataPoint(Point As Point3d, ByVal View As View)
    Dim vertices() As Point3d, tolerance As Double
    On Error GoTo Failed
    TerrainCheckContext
    If Not mHaveFirst Then
        mFirst = Point: mHaveFirst = True
        ShowPrompt "Pick opposite corner. Preview is temporary; no DGN element will be added."
        CommandState.StartDynamics
    Else
        tolerance = 2# / ActiveModelReference.UORsPerMasterUnit
        TerrainRequire Abs(Point.x - mFirst.x) > tolerance And Abs(Point.y - mFirst.y) > tolerance, "Rectangle needs positive XY width and height."
        RectangleVertices Point, vertices
        TerrainAcceptBoundary vertices
        Finish
    End If
    Exit Sub
Failed:
    ShowPrompt Err.Description
End Sub

Private Sub IPrimitiveCommandEvents_Dynamics(Point As Point3d, ByVal View As View, ByVal DrawMode As MsdDrawingMode)
    Dim vertices() As Point3d, preview As LineElement
    On Error GoTo Failed
    TerrainCheckContext
    If Not mHaveFirst Then Exit Sub
    RectangleVertices Point, vertices
    Set preview = CreateLineElement1(Nothing, vertices)
    preview.Redraw DrawMode
    Exit Sub
Failed:
    ShowPrompt Err.Description
End Sub

Public Sub StopPick()
    mFinishing = True
    CommandState.StartDefaultCommand
End Sub

Private Sub Finish()
    StopPick
    TerrainPickerEnded
End Sub

Private Sub IPrimitiveCommandEvents_Reset()
    Finish
End Sub
Private Sub IPrimitiveCommandEvents_Cleanup()
    If Not mFinishing Then TerrainPickerEnded
End Sub
Private Sub IPrimitiveCommandEvents_Keyin(ByVal Keyin As String)
End Sub

Private Sub ILocateCommandEvents_Start()
    Dim criteria As LocateCriteria
    Set criteria = CommandState.CreateLocateCriteria(False)
    CommandState.SetLocateCriteria criteria
    ShowCommand "USGS Terrain Downloader - Closed Shape"
    ShowPrompt "Identify a straight-sided shape in the active model, then accept. Reset cancels."
End Sub

Private Sub ILocateCommandEvents_LocateFilter(ByVal Element As Element, Point As Point3d, Accepted As Boolean)
    On Error GoTo Failed
    Accepted = False
    If Element.ModelReference.IsAttachment Then Exit Sub
    If Not Element.ModelReference.IsActive Then Exit Sub
    Accepted = (Element.Type = msdElementTypeShape)
    If Not Accepted Then ShowPrompt "Select a simple closed shape. Complex/curved shapes, holes, cells and references are unsupported."
    Exit Sub
Failed:
    Accepted = False
    ShowPrompt Err.Description
End Sub

Private Sub ILocateCommandEvents_Accept(ByVal Element As Element, Point As Point3d, ByVal View As View)
    Dim vertices() As Point3d
    On Error GoTo Failed
    TerrainCheckContext
    TerrainRequire Element.ModelReference.IsActive And Not Element.ModelReference.IsAttachment, "Select in the active model."
    TerrainRequire Element.Type = msdElementTypeShape, "Only simple closed shapes are supported."
    vertices = Element.AsVertexList.GetVertices
    TerrainAcceptBoundary vertices
    Finish
    Exit Sub
Failed:
    ShowPrompt Err.Description
End Sub

Private Sub ILocateCommandEvents_LocateReset()
    Finish
End Sub
Private Sub ILocateCommandEvents_LocateFailed()
    ShowPrompt "No supported shape found. Reset cancels."
End Sub
Private Sub ILocateCommandEvents_Dynamics(Point As Point3d, ByVal View As View, ByVal DrawMode As MsdDrawingMode)
End Sub
Private Sub ILocateCommandEvents_Cleanup()
    If Not mFinishing Then TerrainPickerEnded
End Sub

Attribute VB_Name = "frmUSGSTerrainDownloader"
Attribute VB_Base = "0{C38DE8FD-93D6-4D93-B5B0-4352CD5CF3C7}{6CD1CF39-6239-478D-9697-6DF4230867D0}"
Attribute VB_GlobalNameSpace = False
Attribute VB_Creatable = False
Attribute VB_PredeclaredId = True
Attribute VB_Exposed = False
Attribute VB_TemplateDerived = False
Attribute VB_Customizable = False
Option Explicit

' Paste into a blank UserForm named frmUSGSTerrainDownloader. No designer controls required.
Private WithEvents cmdRectangle As MSForms.CommandButton
Attribute cmdRectangle.VB_VarHelpID = -1
Private WithEvents cmdShape As MSForms.CommandButton
Attribute cmdShape.VB_VarHelpID = -1
Private WithEvents cmdBrowse As MSForms.CommandButton
Attribute cmdBrowse.VB_VarHelpID = -1
Private WithEvents cmdSearch As MSForms.CommandButton
Attribute cmdSearch.VB_VarHelpID = -1
Private WithEvents cmdProcess As MSForms.CommandButton
Attribute cmdProcess.VB_VarHelpID = -1
Private WithEvents cmdCancel As MSForms.CommandButton
Attribute cmdCancel.VB_VarHelpID = -1
Private WithEvents cmdOpen As MSForms.CommandButton
Attribute cmdOpen.VB_VarHelpID = -1
Private WithEvents lstProducts As MSForms.ListBox
Attribute lstProducts.VB_VarHelpID = -1
Private txtCRS As MSForms.TextBox, txtResolution As MSForms.TextBox
Private txtVertical As MSForms.TextBox, txtEvidence As MSForms.TextBox
Private txtRoot As MSForms.TextBox, txtPython As MSForms.TextBox
Private txtEnv As MSForms.TextBox, txtOutput As MSForms.TextBox, txtCap As MSForms.TextBox
Private txtDetails As MSForms.TextBox
Private cboMaster As MSForms.ComboBox, cboOutput As MSForms.ComboBox
Private cboSourceZ As MSForms.ComboBox, cboDataset As MSForms.ComboBox
Private chkConfirmed As MSForms.CheckBox, chkClip As MSForms.CheckBox
Private chkOverlap As MSForms.CheckBox, chkGaps As MSForms.CheckBox, chkUnknown As MSForms.CheckBox
Private lblExtent As MSForms.Label, lblStatus As MSForms.Label, lblTotals As MSForms.Label
Private mBusy As Boolean, mJob As String, mSearchFolder As String, mLastFolder As String
Private mRows() As String
Private mVerticalSelection As String, mDetectedVertical As Boolean
Private mDefaultResolution As String

Private Function Label(ByVal name As String, ByVal caption As String, ByVal x As Single, ByVal y As Single, ByVal w As Single, Optional ByVal h As Single = 18) As MSForms.Label
    Set Label = Me.Controls.Add("Forms.Label.1", name, True)
    With Label
        .caption = caption: .Left = x: .Top = y: .Width = w: .Height = h
    End With
End Function

Private Function Box(ByVal name As String, ByVal caption As String, ByVal x As Single, ByVal y As Single, ByVal w As Single, Optional ByVal value As String = "") As MSForms.TextBox
    Dim heading As MSForms.Label
    Set heading = Label("lbl" & name, caption, x, y + 3, 120)
    Set Box = Me.Controls.Add("Forms.TextBox.1", name, True)
    With Box
        .Left = x + 122: .Top = y: .Width = w: .Height = 21: .value = value
    End With
End Function

Private Function Button(ByVal name As String, ByVal caption As String, ByVal x As Single, ByVal y As Single, ByVal w As Single) As MSForms.CommandButton
    Set Button = Me.Controls.Add("Forms.CommandButton.1", name, True)
    With Button
        .caption = caption: .Left = x: .Top = y: .Width = w: .Height = 26
    End With
End Function

Private Function Check(ByVal name As String, ByVal caption As String, ByVal x As Single, ByVal y As Single, ByVal w As Single, Optional ByVal checked As Boolean = False) As MSForms.CheckBox
    Set Check = Me.Controls.Add("Forms.CheckBox.1", name, True)
    With Check
        .caption = caption: .Left = x: .Top = y: .Width = w: .Height = 22: .value = checked
    End With
End Function

Private Function Choices(ByVal name As String, ByVal x As Single, ByVal y As Single, ByVal w As Single, ByVal values As String, Optional ByVal index As Long = -1) As MSForms.ComboBox
    Dim item As Variant
    Set Choices = Me.Controls.Add("Forms.ComboBox.1", name, True)
    With Choices
        .Left = x: .Top = y: .Width = w: .Height = 21: .Style = fmStyleDropDownList
        For Each item In Split(values, "|")
            .AddItem CStr(item)
        Next item
        .ListIndex = index
    End With
End Function

Private Sub UserForm_Initialize()
    Dim heading As MSForms.Label, folder As String, fs As Object
    Dim sourceRoot As String, pythonExe As String, environmentFile As String, master As MeasurementUnit, unitName As String
    TerrainRuntimeDefaults sourceRoot, pythonExe, environmentFile
    Me.caption = "USGS Terrain Downloader"
    Me.Width = 806: Me.Height = 690: Me.ScrollHeight = 781: Me.ScrollBars = fmScrollBarsVertical
    Me.StartUpPosition = 1: Me.Font.name = "Segoe UI": Me.Font.size = 9
    Set heading = Label("lblTitle", "USGS TERRAIN DOWNLOADER", 18, 12, 740, 25)
    heading.Font.size = 14: heading.Font.Bold = True
    Set heading = Label("lblBoundary", "BOUNDARY / PROJECT COORDINATES", 18, 45, 365)
    heading.Font.Bold = True
    Set cmdRectangle = Button("cmdRectangle", "Draw Rectangle", 18, 67, 165)
    Set cmdShape = Button("cmdShape", "Select Existing Shape", 195, 67, 185)
    Set heading = Label("lblGCS", TerrainDetectedGCS(), 18, 100, 365, 38)
    Set txtCRS = Box("txtCRS", "Source EPSG / WKT", 18, 141, 240, TerrainSuggestedCRS())
    txtCRS.ControlTipText = "Suggested from the assigned GCS's EPSG source reference when available. Verify the complete CRS, units and grid mapping; local modifiers are unsupported."
    Set heading = Label("lblMaster", "Model master unit", 18, 173, 120)
    Set cboMaster = Choices("cboMaster", 140, 170, 240, "m|ft|us-ft")
    master = ActiveModelReference.MasterUnit: unitName = TerrainMasterUnitName(master)
    If Len(unitName) > 0 Then cboMaster.value = unitName
    Set chkConfirmed = Check("chkConfirmed", "I verified CRS, master units and grid XY; no local offsets, rotation, ground scale or GCS modifiers.", 18, 198, 365)
    chkConfirmed.Height = 38
    Set lblExtent = Label("lblExtent", TerrainModelDescription() & vbCrLf & "Select boundary; Search calculates WGS84 extent.", 18, 244, 365, 52)
    Set heading = Label("lblProcessing", "PROCESSING / VERTICAL EVIDENCE", 410, 45, 365)
    heading.Font.Bold = True
    Set chkClip = Check("chkClip", "Clip to original selected boundary", 410, 67, 365, True)
    Set heading = Label("lblSourceZ", "Source elevation unit", 410, 100, 120)
    Set cboSourceZ = Choices("cboSourceZ", 532, 97, 240, "m|ft|us-ft")
    Set txtVertical = Box("txtVertical", "Source vertical CRS", 410, 125, 240)
    txtVertical.ControlTipText = "For example EPSG:5703 ONLY when NAVD88 is verified in selected source metadata. No datum shift is performed."
    Set txtEvidence = Box("txtEvidence", "Metadata citation", 410, 153, 240)
    txtEvidence.ControlTipText = "Filled from explicit selected-product declarations when they all agree; otherwise enter verified source metadata citations."
    Set heading = Label("lblOutputZ", "Output elevation unit", 410, 184, 120)
    Set cboOutput = Choices("cboOutput", 532, 181, 240, "m|ft|us-ft", 0)
    Set txtResolution = Box("txtResolution", "Cell size (CRS units)", 410, 209, 240)
    txtResolution.ControlTipText = "After Search, 1-metre DEMs suggest one metre in the confirmed horizontal CRS units. Editable; other datasets require a choice."
    Set chkOverlap = Check("chkOverlap", "Accept overlaps: last selected list row wins", 410, 237, 365)
    Set chkGaps = Check("chkGaps", "Allow/report NoData gaps inside boundary", 410, 263, 365)
    Set heading = Label("lblFixed", "Compatible tiles are mosaicked and reprojected to source DGN CRS. Originals are preserved. Not survey-grade. Fence and automatic ORD attachment are not enabled.", 18, 303, 754, 28)
    Set heading = Label("lblDataset", "USGS data source", 18, 341, 120)
    Set cboDataset = Choices("cboDataset", 140, 338, 320, "3DEP 1-meter DEM|3DEP 1/3-arc-second DEM|LiDAR LAS/LAZ (download only)", 0)
    Set txtCap = Box("txtCap", "Download cap (GiB)", 480, 338, 170, "5")
    Set heading = Label("lblColumns", "Select products after Search. Columns: product / resolution / publication date / estimated MiB", 18, 370, 754)
    Set lstProducts = Me.Controls.Add("Forms.ListBox.1", "lstProducts", True)
    With lstProducts
        .Left = 18: .Top = 391: .Width = 754: .Height = 96
        .ColumnCount = 4: .ColumnWidths = "440 pt;90 pt;100 pt;95 pt"
        .MultiSelect = fmMultiSelectMulti
    End With
    Set txtDetails = Me.Controls.Add("Forms.TextBox.1", "txtDetails", True)
    With txtDetails
        .Left = 18: .Top = 495: .Width = 754: .Height = 56
        .Multiline = True: .Locked = True: .ScrollBars = fmScrollBarsBoth
        .value = "Product metadata will appear here. Publication date is not an accuracy ranking. Verify source vertical datum/unit before processing."
    End With
    Set lblTotals = Label("lblTotals", "No products selected.", 18, 559, 450)
    Set chkUnknown = Check("chkUnknown", "Accept unknown sizes within hard cap", 480, 555, 292)
    Set txtRoot = Box("txtRoot", "Source code folder", 18, 585, 632, sourceRoot)
    txtRoot.ControlTipText = "Full path to USGSTerrainDownloader folder containing python\launch_worker.exe and main.py."
    Set txtPython = Box("txtPython", "Python executable", 18, 613, 632, pythonExe)
    Set txtEnv = Box("txtEnv", "GIS environment JSON", 18, 641, 632, environmentFile)
    txtEnv.ControlTipText = "Optional child environment JSON. See python\osgeo4w-environment.example.json."
    folder = TerrainDefaultDestination()
    Set txtOutput = Box("txtOutput", "Destination folder", 18, 669, 540, folder)
    Set cmdBrowse = Button("cmdBrowse", "Browse...", 688, 666, 84)
    Set lblStatus = Label("lblStatus", "Ready. Draw/select boundary, confirm coordinates, then Search USGS.", 18, 703, 754, 28)
    Set cmdSearch = Button("cmdSearch", "Search USGS", 18, 741, 140)
    Set cmdProcess = Button("cmdProcess", "Download / Process", 170, 741, 170)
    Set cmdOpen = Button("cmdOpen", "Open Output Folder", 352, 741, 170)
    Set cmdCancel = Button("cmdCancel", "Cancel / Close", 632, 741, 140)
    cmdCancel.Cancel = True
    cmdRectangle.Accelerator = "R": cmdShape.Accelerator = "E"
    cmdSearch.Accelerator = "S": cmdProcess.Accelerator = "D"
    cmdOpen.Accelerator = "O": cmdBrowse.Accelerator = "B"
End Sub

Public Sub BoundaryChanged(ByVal message As String)
    mSearchFolder = "": lstProducts.Clear
    lblExtent.caption = message: lblTotals.caption = "Search required for new boundary."
End Sub

Private Sub cmdRectangle_Click()
    If Not mBusy Then TerrainPick True
End Sub
Private Sub cmdShape_Click()
    If Not mBusy Then TerrainPick False
End Sub
Private Sub cmdBrowse_Click()
    Dim path As String
    path = TerrainBrowseFolder("Choose a writable project terrain-data folder")
    If Len(path) > 0 Then txtOutput.value = path
End Sub

Private Function DatasetKey() As String
    Select Case cboDataset.ListIndex
        Case 0: DatasetKey = "dem1m"
        Case 1: DatasetKey = "dem13"
        Case 2: DatasetKey = "lidar"
        Case Else: TerrainRequire False, "Select a USGS dataset."
    End Select
End Function

Private Function RequestJSON(ByVal action As String) As String
    Dim result As String, ids As String, i As Long, fields As Variant, cap As Double, resolution As Double
    TerrainCheckContext True
    TerrainRequire chkConfirmed.value And Len(Trim$(txtCRS.text)) > 0 And cboMaster.ListIndex >= 0, "Explicitly verify source CRS, model master units and grid-coordinate mapping."
    result = "{""schema_version"":1,""action"":" & TerrainQuoteJSON(action) & _
        ",""boundary"":" & TerrainBoundaryJSON() & ",""source_crs"":" & TerrainQuoteJSON(Trim$(txtCRS.text)) & _
        ",""master_unit"":" & TerrainQuoteJSON(cboMaster.value) & ",""crs_confirmed"":true,""coordinates_are_grid"":true" & _
        ",""dataset"":" & TerrainQuoteJSON(DatasetKey()) & ",""python_executable"":" & TerrainQuoteJSON(Trim$(txtPython.text)) & _
        ",""environment_file"":" & TerrainQuoteJSON(Trim$(txtEnv.text)) & ",""dgn_context"":" & TerrainQuoteJSON(TerrainModelDescription()) & _
        ",""dgn_gcs_probe"":" & TerrainQuoteJSON(TerrainDetectedGCS())
    If action = "process" Then
        TerrainRequire Len(mSearchFolder) > 0, "Search USGS first."
        For i = 0 To lstProducts.ListCount - 1
            If lstProducts.selected(i) Then
                fields = Split(mRows(i), vbTab)
                If Len(ids) > 0 Then ids = ids & ","
                ids = ids & TerrainQuoteJSON(CStr(fields(0)))
            End If
        Next i
        TerrainRequire Len(ids) > 0, "Select at least one product."
        TerrainRequire IsNumeric(txtCap.text), "Download cap must be numeric GiB."
        cap = CDbl(txtCap.text)
        TerrainRequire cap > 0 And cap <= 100, "Download cap must be > 0 and <= 100 GiB."
        result = result & ",""selected_ids"": [" & ids & "],""search_manifest"":" & TerrainQuoteJSON(mSearchFolder & "\search.json") & _
            ",""max_download_bytes"":" & Format$(Fix(cap * 1073741824#), "0") & _
            ",""unknown_size_confirmed"":" & TerrainBool(chkUnknown.value)
        If DatasetKey() <> "lidar" Then
            TerrainRequire cboSourceZ.ListIndex >= 0 And Len(Trim$(txtVertical.text)) > 0 And Len(Trim$(txtEvidence.text)) >= 12, "Verify selected sources' vertical datum/unit and enter source metadata evidence. Mixed datums are unsupported."
            TerrainRequire IsNumeric(txtResolution.text), "Cell size must be numeric in source CRS native horizontal units."
            resolution = CDbl(txtResolution.text)
            TerrainRequire resolution > 0, "Cell size must be positive."
            result = result & ",""source_vertical"": {""unit"":" & TerrainQuoteJSON(cboSourceZ.value) & _
                ",""crs"":" & TerrainQuoteJSON(Trim$(txtVertical.text)) & ",""evidence"":" & TerrainQuoteJSON(Trim$(txtEvidence.text)) & "}" & _
                ",""resolution"":" & TerrainNumber(resolution) & ",""elevation_unit"":" & TerrainQuoteJSON(cboOutput.value) & _
                ",""clip"":" & TerrainBool(chkClip.value) & ",""overlap_order_confirmed"":" & TerrainBool(chkOverlap.value) & _
                ",""allow_gaps"":" & TerrainBool(chkGaps.value)
        End If
    End If
    RequestJSON = result & "}"
End Function

Private Sub SetBusy(ByVal busy As Boolean)
    Dim control As MSForms.control
    mBusy = busy
    For Each control In Me.Controls
        If TypeName(control) <> "Label" Then control.Enabled = Not busy
    Next control
    cmdCancel.Enabled = True
    If Not busy Then cboSourceZ.Enabled = Not mDetectedVertical
End Sub

Private Sub RunWorker(ByVal action As String)
    Dim request As String, worker As Object, text As String, errorText As String
    On Error GoTo Failed
    If mBusy Then Exit Sub
    request = RequestJSON(action)
    SaveSetting "USGSTerrainDownloader", "Runtime", "SourceRoot", Trim$(txtRoot.text)
    SaveSetting "USGSTerrainDownloader", "Runtime", "Python", Trim$(txtPython.text)
    SaveSetting "USGSTerrainDownloader", "Runtime", "EnvironmentFile", Trim$(txtEnv.text)
    mJob = TerrainNewJobFolder(Trim$(txtOutput.text)): mLastFolder = mJob
    TerrainWriteUTF8 mJob & "\request.json", request
    If action = "search" Then mSearchFolder = "": lstProducts.Clear
    SetBusy True
    lblStatus.caption = "Starting " & action & "..."
    Set worker = TerrainStartWorker(Trim$(txtRoot.text), mJob & "\request.json")
    Do While worker.status = 0
        text = TerrainReadUI(mJob & "\status.txt")
        If Len(text) > 0 Then lblStatus.caption = Replace(text, vbCrLf, ": ")
        TerrainYield
    Loop
    text = TerrainReadUI(mJob & "\status.txt")
    If Len(text) > 0 Then lblStatus.caption = Replace(text, vbCrLf, ": ")
    TerrainRequire worker.ExitCode = 0, "Worker failed/cancelled. " & text & vbCrLf & "See " & mJob & "\error.log. If Python did not start, verify runtime paths and launcher permissions."
    If action = "search" Then
        mSearchFolder = mJob
        LoadProducts
        lblExtent.caption = TerrainReadUI(mJob & "\extent.txt")
    End If
    SetBusy False
    Exit Sub
Failed:
    errorText = Err.Description
    On Error Resume Next
    If Not worker Is Nothing Then
        If worker.status = 0 Then
            TerrainCancelJob mJob
            Do While worker.status = 0
                TerrainYield
            Loop
        End If
    End If
    On Error GoTo 0
    SetBusy False
    lblStatus.caption = errorText
    MsgBox errorText, vbExclamation, "USGS Terrain Downloader"
End Sub

Private Sub LoadProducts()
    Dim contents As String, i As Long, fields As Variant, size As String, suggested As String
    suggested = Trim$(TerrainReadUI(mSearchFolder & "\cell-size.txt"))
    If Len(suggested) > 0 Then suggested = CStr(Val(suggested))
    If Len(Trim$(txtResolution.text)) = 0 Or txtResolution.text = mDefaultResolution Then txtResolution.value = suggested
    mDefaultResolution = suggested
    lstProducts.Clear
    contents = TerrainReadUI(mSearchFolder & "\products.tsv")
    If Len(contents) = 0 Then Exit Sub
    mRows = Split(contents, vbCrLf)
    For i = 0 To UBound(mRows)
        fields = Split(mRows(i), vbTab)
        TerrainRequire UBound(fields) = 11, "Invalid products.tsv row. Update the worker and MVBA together."
        size = "unknown"
        If IsNumeric(fields(2)) Then size = Format$(CDbl(fields(2)) / 1048576#, "0.0")
        lstProducts.AddItem fields(1)
        lstProducts.List(i, 1) = fields(4): lstProducts.List(i, 2) = fields(3): lstProducts.List(i, 3) = size
    Next i
    RefreshTotals
End Sub

Private Sub RefreshTotals()
    Dim i As Long, count As Long, total As Double, unknown As Long, fields As Variant
    ' ListBox Change can fire before Initialize creates the totals label.
    If lblTotals Is Nothing Then Exit Sub
    For i = 0 To lstProducts.ListCount - 1
        If lstProducts.selected(i) Then
            count = count + 1: fields = Split(mRows(i), vbTab)
            If IsNumeric(fields(2)) Then total = total + CDbl(fields(2)) Else unknown = unknown + 1
        End If
    Next i
    lblTotals.caption = CStr(count) & " / " & CStr(lstProducts.ListCount) & " selected; known estimate " & Format$(total / 1073741824#, "0.000") & " GiB; " & CStr(unknown) & " unknown sizes."
End Sub

Private Sub RefreshVerticalMetadata()
    Dim i As Long, count As Long, fields As Variant, key As String
    Dim unit As String, crs As String, evidence As String, available As Boolean
    available = True
    For i = 0 To lstProducts.ListCount - 1
        If lstProducts.selected(i) Then
            fields = Split(mRows(i), vbTab)
            key = key & CStr(Len(fields(0))) & ":" & fields(0)
            count = count + 1
            If count = 1 Then unit = fields(9): crs = fields(10)
            If Len(fields(9)) = 0 Or Len(fields(10)) = 0 Or Len(fields(11)) = 0 Then available = False
            If fields(9) <> unit Or fields(10) <> crs Then available = False
            If Len(evidence) > 0 Then evidence = evidence & " | "
            evidence = evidence & fields(11)
        End If
    Next i
    If key = mVerticalSelection Then Exit Sub
    mVerticalSelection = key
    mDetectedVertical = available And count > 0
    cboSourceZ.ListIndex = -1: txtVertical.value = "": txtEvidence.value = ""
    If mDetectedVertical Then
        cboSourceZ.value = unit: txtVertical.value = crs: txtEvidence.value = evidence
    End If
    cboSourceZ.Enabled = Not mBusy And Not mDetectedVertical
    txtVertical.Locked = mDetectedVertical: txtEvidence.Locked = mDetectedVertical
    If Not lblStatus Is Nothing And count > 0 Then
        If mDetectedVertical Then
            lblStatus.caption = "Source vertical units/datum read from selected product metadata; citations saved automatically."
        Else
            lblStatus.caption = "Selected metadata is missing or disagrees. Verify all selected sources before entering vertical units/datum/evidence."
        End If
    End If
End Sub

Private Sub lstProducts_Change()
    Dim fields As Variant
    If lstProducts.ListIndex >= 0 Then
        fields = Split(mRows(lstProducts.ListIndex), vbTab)
        txtDetails.value = "Coverage: " & fields(5) & vbCrLf & "Metadata: " & fields(7) & vbCrLf & fields(8)
    End If
    RefreshTotals
    RefreshVerticalMetadata
End Sub
Private Sub cmdSearch_Click()
    RunWorker "search"
End Sub
Private Sub cmdProcess_Click()
    RunWorker "process"
End Sub
Private Sub cmdOpen_Click()
    On Error GoTo Failed
    If Len(mLastFolder) > 0 Then TerrainOpenFolder mLastFolder Else TerrainOpenFolder txtOutput.text
    Exit Sub
Failed:
    MsgBox Err.Description, vbExclamation, "Output folder"
End Sub
Private Sub cmdCancel_Click()
    If mBusy Then
        TerrainCancelJob mJob
        lblStatus.caption = "Cancellation requested. Waiting for current network/GDAL operation to stop..."
    Else
        Unload Me
    End If
End Sub
Private Sub UserForm_QueryClose(Cancel As Integer, CloseMode As Integer)
    If mBusy Then
        Cancel = True
        TerrainCancelJob mJob
        lblStatus.caption = "Cancellation requested. Dialog will remain until worker stops."
    Else
        TerrainClose
    End If
End Sub

Attribute VB_Name = "modPythonBridge"
Option Explicit

#If VBA7 Then
Private Declare PtrSafe Sub Sleep Lib "kernel32" (ByVal milliseconds As Long)
#Else
Private Declare Sub Sleep Lib "kernel32" (ByVal milliseconds As Long)
#End If

Public Function TerrainQuoteJSON(ByVal value As String) As String
    Dim i As Long, code As Long, ch As String, result As String
    result = Chr$(34)
    For i = 1 To Len(value)
        ch = Mid$(value, i, 1): code = AscW(ch)
        Select Case code
            Case 34: result = result & "\" & Chr$(34)
            Case 92: result = result & "\\"
            Case 0 To 31: result = result & "\u" & Right$("0000" & Hex$(code), 4)
            Case Else: result = result & ch
        End Select
    Next i
    TerrainQuoteJSON = result & Chr$(34)
End Function

Public Function TerrainBool(ByVal value As Boolean) As String
    If value Then TerrainBool = "true" Else TerrainBool = "false"
End Function

Public Sub TerrainWriteUTF8(ByVal path As String, ByVal text As String)
    Dim stream As Object
    Set stream = CreateObject("ADODB.Stream")
    stream.Type = 2: stream.Charset = "utf-8": stream.Open
    stream.WriteText text
    stream.SaveToFile path, 2
    stream.Close
End Sub
Public Function TerrainReadUI(ByVal path As String) As String
    Dim fs As Object, stream As Object, attempt As Long, contents As String
    Dim errorNumber As Long, errorText As String
    Set fs = CreateObject("Scripting.FileSystemObject")
    For attempt = 1 To 20
        contents = ""
        On Error Resume Next
        Err.Clear
        If fs.FileExists(path) Then
            Set stream = fs.OpenTextFile(path, 1, False, -1)
            If Err.number = 0 Then
                If Not stream.AtEndOfStream Then contents = stream.ReadAll
            End If
        End If
        errorNumber = Err.number: errorText = Err.Description
        If Not stream Is Nothing Then stream.Close
        Set stream = Nothing
        On Error GoTo 0
        If errorNumber = 0 Then
            TerrainReadUI = contents
            Exit Function
        End If
        If errorNumber <> 70 And errorNumber <> 75 And errorNumber <> 53 Then Exit For
        ' A sync/scanner handle or atomic replacement may briefly deny this read.
        If attempt < 20 Then Sleep 50
    Next attempt
    Err.Raise errorNumber, "TerrainReadUI", "Cannot read " & path & " (" & CStr(errorNumber) & "): " & errorText
End Function


Public Sub TerrainRuntimeDefaults(ByRef sourceRoot As String, ByRef pythonExe As String, ByRef environmentFile As String)
    Dim fs As Object, project As Object, candidate As String, matches As Long
    Dim config As String, stream As Object
    sourceRoot = GetSetting("USGSTerrainDownloader", "Runtime", "SourceRoot", "")
    pythonExe = GetSetting("USGSTerrainDownloader", "Runtime", "Python", "")
    environmentFile = GetSetting("USGSTerrainDownloader", "Runtime", "EnvironmentFile", "")
    On Error GoTo Unavailable
    Set fs = CreateObject("Scripting.FileSystemObject")
    If Len(sourceRoot) = 0 Then
        For Each project In Application.VBE.VBProjects
            If project.name = "USGSTerrainDownloader" Then
                matches = matches + 1
                candidate = fs.GetParentFolderName(project.FileName)
            End If
        Next project
        If matches = 1 Then
            If fs.FileExists(fs.BuildPath(candidate, "python\launch_worker.exe")) Then sourceRoot = candidate
        End If
    End If
    config = Environ$("LOCALAPPDATA") & "\USGSTerrainDownloaderConfig"
    If Len(environmentFile) = 0 And fs.FileExists(config & "\runtime-environment.json") Then environmentFile = config & "\runtime-environment.json"
    If Len(pythonExe) = 0 And fs.FileExists(config & "\runtime-python.txt") Then
        Set stream = CreateObject("ADODB.Stream")
        stream.Type = 2: stream.Charset = "utf-8": stream.Open
        stream.LoadFromFile config & "\runtime-python.txt"
        candidate = Trim$(stream.ReadText): stream.Close
        If fs.FileExists(candidate) And LCase$(fs.GetExtensionName(candidate)) = "exe" Then pythonExe = candidate
    End If
Unavailable:
    ' Discovery is optional; unavailable paths remain editable, never guessed.
End Sub
Public Function TerrainNewJobFolder(ByVal destination As String, Optional ByVal action As String = "run") As String
    Dim fs As Object, path As String, base As String, prefix As String, number As Long
    Dim errorNumber As Long, errorText As String
    Set fs = CreateObject("Scripting.FileSystemObject")
    TerrainRequire fs.FolderExists(destination), "Destination must be an existing writable folder. Browse or create it first."
    TerrainRequire action = "search" Or action = "process" Or action = "run", "Unknown job folder purpose."
    prefix = action
    If action = "process" Then prefix = "terrain"
    base = fs.BuildPath(destination, prefix & "-" & Format$(Now, "yyyy-mm-dd_hh-nn-ss"))
    number = 1
    Do
        path = base
        If number > 1 Then path = base & "-" & Format$(number, "00")
        On Error Resume Next
        Err.Clear
        fs.CreateFolder path
        errorNumber = Err.number: errorText = Err.Description
        On Error GoTo 0
        If errorNumber = 0 Then
            TerrainNewJobFolder = path
            Exit Function
        End If
        If errorNumber <> 58 Then Err.Raise errorNumber, "TerrainNewJobFolder", "Cannot create " & path & ": " & errorText
        number = number + 1
    Loop
End Function


Private Function CommandQuote(ByVal value As String) As String
    TerrainRequire InStr(value, Chr$(34)) = 0 And InStr(value, vbCr) = 0 And InStr(value, vbLf) = 0, "Invalid command path."
    TerrainRequire Right$(value, 1) <> "\", "Command argument cannot end in a slash."
    CommandQuote = Chr$(34) & value & Chr$(34)
End Function

Public Function TerrainStartWorker(ByVal sourceRoot As String, ByVal requestPath As String) As Object
    Dim shell As Object, fs As Object, launcher As String
    Set fs = CreateObject("Scripting.FileSystemObject")
    launcher = fs.BuildPath(sourceRoot, "python\launch_worker.exe")
    TerrainRequire fs.FileExists(launcher), "Source folder must contain python\launch_worker.exe beside main.py."
    Set shell = CreateObject("WScript.Shell")
    Set TerrainStartWorker = shell.Exec(CommandQuote(launcher) & " " & CommandQuote(requestPath))
End Function

Public Sub TerrainYield()
    DoEvents
    Sleep 100
End Sub

Public Sub TerrainCancelJob(ByVal folder As String)
    If Len(folder) > 0 Then TerrainWriteUTF8 folder & "\cancel.flag", "cancel"
End Sub

Public Function TerrainBrowseFolder(ByVal title As String) As String
    Dim shell As Object, folder As Object
    Set shell = CreateObject("Shell.Application")
    Set folder = shell.BrowseForFolder(0, title, 0)
    If Not folder Is Nothing Then TerrainBrowseFolder = folder.Self.path
End Function

Public Sub TerrainOpenFolder(ByVal path As String)
    Dim shell As Object, fs As Object
    Set fs = CreateObject("Scripting.FileSystemObject")
    TerrainRequire fs.FolderExists(path), "Folder does not exist."
    Set shell = CreateObject("Shell.Application")
    shell.Explore path
End Sub

Public Function TerrainDefaultDestination() As String
    Dim fs As Object, folder As String, stream As Object, probe As String
    On Error GoTo LocalFallback
    Set fs = CreateObject("Scripting.FileSystemObject")
    TerrainRequire Len(ActiveDesignFile.path) > 0, "DGN has no project folder."
    folder = fs.BuildPath(ActiveDesignFile.path, "USGS_Terrain")
    If Not fs.FolderExists(folder) Then fs.CreateFolder folder
    probe = fs.BuildPath(folder, fs.GetTempName)
    Set stream = fs.CreateTextFile(probe, False): stream.Close
    fs.DeleteFile probe
    TerrainDefaultDestination = folder
    Exit Function
LocalFallback:
    On Error GoTo Failed
    Set fs = CreateObject("Scripting.FileSystemObject")
    folder = Environ$("LOCALAPPDATA") & "\USGSTerrainDownloader"
    If Not fs.FolderExists(folder) Then fs.CreateFolder folder
    TerrainDefaultDestination = folder
    Exit Function
Failed:
    TerrainDefaultDestination = Environ$("TEMP")
End Function

Attribute VB_Name = "modTerrainCoordinates"
Option Explicit

Public Function TerrainNumber(ByVal value As Double) As String
    ' Str$ uses a period even on decimal-comma Windows installations.
    TerrainNumber = Trim$(Str$(value))
    If Left$(TerrainNumber, 1) = "." Then TerrainNumber = "0" & TerrainNumber
    If Left$(TerrainNumber, 2) = "-." Then TerrainNumber = "-0" & Mid$(TerrainNumber, 2)
End Function

Public Function TerrainVerticesJSON(vertices() As Point3d) As String
    Dim i As Long, result As String, tolerance As Double
    TerrainRequire UBound(vertices) - LBound(vertices) >= 2, "Boundary needs three corners."
    TerrainRequire UBound(vertices) - LBound(vertices) < 20000, "Too many boundary vertices."
    tolerance = 2# / ActiveModelReference.UORsPerMasterUnit
    result = "["
    For i = LBound(vertices) To UBound(vertices)
        TerrainRequire Abs(vertices(i).Z - vertices(LBound(vertices)).Z) <= tolerance, "Select a horizontal shape. Tilted/nonplanar boundaries are unsupported."
        If i > LBound(vertices) Then result = result & ","
        result = result & "[" & TerrainNumber(vertices(i).x) & "," & TerrainNumber(vertices(i).y) & "]"
    Next i
    TerrainVerticesJSON = result & "]"
End Function

Public Function TerrainModelDescription() As String
    Dim master As MeasurementUnit
    master = ActiveModelReference.MasterUnit
    TerrainModelDescription = "Model: " & ActiveModelReference.name & " | master label: " & master.Label & _
        " | UOR/master: " & TerrainNumber(ActiveModelReference.UORsPerMasterUnit)
End Function

Public Function TerrainMasterUnitName(unit As MeasurementUnit) As String
    Dim metres As Double
    If unit.base <> msdMeasurementBaseMeter Then Exit Function
    If unit.UnitsPerBaseNumerator <= 0 Or unit.UnitsPerBaseDenominator <= 0 Then Exit Function
    metres = unit.UnitsPerBaseDenominator / unit.UnitsPerBaseNumerator
    ' Labels such as a prime do not distinguish international and US survey feet.
    If Abs(metres - 1#) < 0.000000000001 Then TerrainMasterUnitName = "m"
    If Abs(metres - 0.3048) < 0.000000000001 Then TerrainMasterUnitName = "ft"
    If Abs(metres - 1200# / 3937#) < 0.000000000001 Then TerrainMasterUnitName = "us-ft"
End Function

Public Function TerrainEPSGReference(ByVal source As String) As String
    Dim code As String
    source = Trim$(source)
    If UCase$(Left$(source, 5)) <> "EPSG:" Then Exit Function
    code = Trim$(Mid$(source, 6))
    If Len(code) = 0 Then Exit Function
    If Left$(code, 1) = "0" Or code Like "*[!0-9]*" Then Exit Function
    TerrainEPSGReference = "EPSG:" & code
End Function

Public Function TerrainSuggestedCRS() As String
    Dim model As Object, gcs As Object
    On Error GoTo Unavailable
    Set model = ActiveModelReference
    Set gcs = CallByName(model, "GetGCS", VbMethod, True)
    If gcs Is Nothing Then Exit Function
    ' Source is a suggestion; local modifiers and grid mapping still require verification.
    TerrainSuggestedCRS = TerrainEPSGReference(CStr(CallByName(gcs, "Source", VbGet)))
Unavailable:
End Function

Public Function TerrainDetectedGCS() As String
    Dim model As Object, gcs As Object
    On Error GoTo Unavailable
    Set model = ActiveModelReference
    ' shortcut: probe GCS name only; add a verified full-definition adapter for automatic EPSG/modifier support.
    ' Bentley COM GetGCS(True) reads the model GCS, not a guessed EPSG mapping.
    Set gcs = CallByName(model, "GetGCS", VbMethod, True)
    If gcs Is Nothing Then GoTo Unavailable
    TerrainDetectedGCS = CStr(CallByName(gcs, "Name", VbGet))
    If Len(TerrainDetectedGCS) = 0 Then GoTo Unavailable
    TerrainDetectedGCS = "Bentley GCS name: " & TerrainDetectedGCS & ". Confirm equivalent EPSG/WKT and model units below."
    Exit Function
Unavailable:
    TerrainDetectedGCS = "DGN GCS unavailable through COM. Explicit, verified EPSG/WKT and master units are REQUIRED."
End Function
