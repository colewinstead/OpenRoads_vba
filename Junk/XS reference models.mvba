Attribute VB_Name = "Module1"
Option Explicit

' =========================================================
' CONSTANTS (safe for OpenRoads / MicroStation VBA)
' =========================================================
Private Const MODELTYPE_SHEET As Long = 2   ' msdModelTypeSheet is typically 2


' =========================================================
' MAIN: LOOP ALL MODELS IN THE CURRENT (MAIN) DGN
' =========================================================
Public Sub AttachXS_ByStation_Keyin_AllModels()

    Dim refDgnPath As String
    refDgnPath = PickDgnFile("Select the reference DGN (contains ALL XS models)")
    If Len(refDgnPath) = 0 Then Exit Sub

    ' Cache reference models by station (so we don't reopen the ref DGN for every model)
    Dim dictAny As Object, dict2D As Object, dict3D As Object
    Set dictAny = CreateObject("Scripting.Dictionary")
    Set dict2D = CreateObject("Scripting.Dictionary")
    Set dict3D = CreateObject("Scripting.Dictionary")

    BuildRefStationIndex refDgnPath, dictAny, dict2D, dict3D

    If dictAny.Count = 0 And dict2D.Count = 0 And dict3D.Count = 0 Then
        MsgBox "No usable (non-sheet) station models were found in the reference DGN:" & vbCrLf & refDgnPath, vbExclamation
        Exit Sub
    End If

    Dim mainDF As DesignFile
    Set mainDF = ActiveDesignFile

    ' Remember starting model so we can return to it
    Dim startModelName As String
    startModelName = ActiveModelReference.Name

    ' Build a stable list of model names first (avoids enumeration issues while activating models)
    Dim names As Collection
    Set names = New Collection

    Dim m As ModelReference
    For Each m In mainDF.Models
        names.Add m.Name
    Next m

    Dim attached As Long, skippedSheets As Long, skippedNoStation As Long, skippedNoMatch As Long, skippedAlready As Long, failedAttach As Long
    attached = 0: skippedSheets = 0: skippedNoStation = 0: skippedNoMatch = 0: skippedAlready = 0: failedAttach = 0

    Dim nm As Variant
    For Each nm In names

        Dim mr As ModelReference
        Set mr = GetModelByName(mainDF, CStr(nm))
        If mr Is Nothing Then GoTo NextModel

        ' Skip sheet models
        If IsSheetModelName(mr.Name) Or SafeGetModelType(mr) = MODELTYPE_SHEET Then
            skippedSheets = skippedSheets + 1
            GoTo NextModel
        End If

        ' Activate this model (attachments apply to the active model)
        mr.Activate
        DoEvents

        Dim activeModelName As String
        activeModelName = ActiveModelReference.Name

        ' Extract station from the active model name
        Dim stationText As String
        Dim stationVal As Double
        stationVal = StationValueFromModelName(activeModelName, stationText)

        If stationText = "" Then
            skippedNoStation = skippedNoStation + 1
            GoTo NextModel
        End If

        ' Pick best match dictionary based on 2D/3D (if exposed)
        Dim is3DVar As Variant
        is3DVar = SafeGetIs3D(ActiveModelReference)

        Dim stationKey As String
        stationKey = StationKeyFromValue(stationVal)

        Dim matchModelName As String
        matchModelName = ""

        If Not IsNull(is3DVar) Then
            If CBool(is3DVar) = True Then
                If dict3D.Exists(stationKey) Then matchModelName = dict3D(stationKey)
            Else
                If dict2D.Exists(stationKey) Then matchModelName = dict2D(stationKey)
            End If
        End If

        ' Fallback to "any" match
        If matchModelName = "" Then
            If dictAny.Exists(stationKey) Then matchModelName = dictAny(stationKey)
        End If

        If matchModelName = "" Then
            skippedNoMatch = skippedNoMatch + 1
            GoTo NextModel
        End If

        ' Logical name based on station so reruns don’t duplicate
        Dim logicalName As String
        logicalName = "XS_" & CleanForLogicalName(stationText)

        If AttachmentExistsByLogicalName(logicalName) Then
            skippedAlready = skippedAlready + 1
            GoTo NextModel
        End If

        ' Attach via keyin (most compatible across ORD builds)
        If AttachByKeyin(refDgnPath, matchModelName, logicalName) Then
            attached = attached + 1
        Else
            failedAttach = failedAttach + 1
        End If

NextModel:
        DoEvents
    Next nm

    ' Return to starting model
    Dim back As ModelReference
    Set back = GetModelByName(mainDF, startModelName)
    If Not back Is Nothing Then back.Activate

    MsgBox "Done attaching XS refs by station." & vbCrLf & vbCrLf & _
           "Attached: " & attached & vbCrLf & _
           "Skipped (Sheet models): " & skippedSheets & vbCrLf & _
           "Skipped (No station in name): " & skippedNoStation & vbCrLf & _
           "Skipped (No station match in ref): " & skippedNoMatch & vbCrLf & _
           "Skipped (Already attached): " & skippedAlready & vbCrLf & _
           "Failed attaches: " & failedAttach, vbInformation

End Sub


' =========================================================
' BUILD REF STATION INDEX (ONE TIME)
' =========================================================
Private Sub BuildRefStationIndex(ByVal refDgnPath As String, ByRef dictAny As Object, ByRef dict2D As Object, ByRef dict3D As Object)
    On Error GoTo EH

    Dim df As DesignFile
    Set df = Application.OpenDesignFileForProgram(refDgnPath, True) ' read-only

    Dim m As ModelReference
    For Each m In df.Models

        ' Skip sheets
        If SafeGetModelType(m) = MODELTYPE_SHEET Then GoTo NextRef
        If IsSheetModelName(m.Name) Then GoTo NextRef

        Dim stText As String
        Dim stVal As Double
        stVal = StationValueFromModelName(m.Name, stText)
        If stText = "" Then GoTo NextRef

        Dim key As String
        key = StationKeyFromValue(stVal)

        ' Always populate "any" (first one wins)
        If Not dictAny.Exists(key) Then dictAny.Add key, m.Name

        ' If 2D/3D is readable, also populate specific dictionary
        Dim is3DVar As Variant
        is3DVar = SafeGetIs3D(m)

        If Not IsNull(is3DVar) Then
            If CBool(is3DVar) = True Then
                If Not dict3D.Exists(key) Then dict3D.Add key, m.Name
            Else
                If Not dict2D.Exists(key) Then dict2D.Add key, m.Name
            End If
        End If

NextRef:
    Next m

    df.Close
    Exit Sub

EH:
    On Error Resume Next
    If Not df Is Nothing Then df.Close
End Sub


' =========================================================
' ATTACH VIA KEYIN (MOST COMPATIBLE)
' =========================================================
Private Function AttachByKeyin(ByVal dgnPath As String, ByVal modelName As String, ByVal logicalName As String) As Boolean
    On Error GoTo EH

    Dim keyin As String
    keyin = "REFERENCE ATTACH " & Q(dgnPath) & "," & Q(modelName) & "," & Q(logicalName)

    CadInputQueue.SendKeyin keyin
    CadInputQueue.SendKeyin "NULL"
    DoEvents

    ' If FindByLogicalName works in your build, confirm quickly
    Dim i As Long
    For i = 1 To 40
        If AttachmentExistsByLogicalName(logicalName) Then
            AttachByKeyin = True
            Exit Function
        End If
        DoEvents
    Next i

    ' If we can't confirm, treat as failure
    AttachByKeyin = False
    Exit Function

EH:
    AttachByKeyin = False
End Function


' =========================================================
' ATTACHMENT EXISTS CHECK (late-bound safe)
' =========================================================
Private Function AttachmentExistsByLogicalName(ByVal logicalName As String) As Boolean
    On Error GoTo EH

    Dim atts As Object
    Set atts = ActiveModelReference.Attachments

    Dim found As Object
    Set found = Nothing

    On Error Resume Next
    Set found = CallByName(atts, "FindByLogicalName", VbMethod, logicalName)
    On Error GoTo EH

    AttachmentExistsByLogicalName = Not (found Is Nothing)
    Exit Function

EH:
    AttachmentExistsByLogicalName = False
End Function


' =========================================================
' MODEL LOOKUP
' =========================================================
Private Function GetModelByName(ByVal df As DesignFile, ByVal modelName As String) As ModelReference
    Dim m As ModelReference
    For Each m In df.Models
        If StrComp(m.Name, modelName, vbTextCompare) = 0 Then
            Set GetModelByName = m
            Exit Function
        End If
    Next m
    Set GetModelByName = Nothing
End Function


' =========================================================
' STATION PARSING
' Accepts: -434+50, -434+50.0000, 434+50.00, etc.
' =========================================================
Private Function StationValueFromModelName(ByVal modelName As String, ByRef stationText As String) As Double
    stationText = ExtractStationText(modelName)
    If stationText = "" Then
        StationValueFromModelName = 1E+99
        Exit Function
    End If

    Dim sign As Double: sign = 1#
    Dim s As String: s = stationText

    If Left$(s, 1) = "-" Then
        sign = -1#
        s = Mid$(s, 2)
    End If

    Dim parts() As String
    parts = Split(s, "+")
    If UBound(parts) <> 1 Then
        stationText = ""
        StationValueFromModelName = 1E+99
        Exit Function
    End If

    Dim majorPart As Double
    Dim minorPart As Double
    majorPart = CDbl(parts(0))
    minorPart = CDbl(parts(1))

    StationValueFromModelName = sign * (majorPart * 100# + minorPart)
End Function

Private Function ExtractStationText(ByVal s As String) As String
    On Error GoTo EH

    Dim re As Object
    Set re = CreateObject("VBScript.RegExp")
    re.Global = False
    re.IgnoreCase = True
    re.Pattern = "(-?\d+\+\d+(?:\.\d+)?)"

    If re.Test(s) Then
        ExtractStationText = re.Execute(s)(0).Value
    Else
        ExtractStationText = ""
    End If
    Exit Function

EH:
    ExtractStationText = ""
End Function

Private Function StationKeyFromValue(ByVal stVal As Double) As String
    ' Round to avoid formatting noise (434+50 vs 434+50.0000 etc.)
    StationKeyFromValue = CStr(Round(stVal, 4))
End Function


' =========================================================
' SAFE GETTERS / HELPERS
' =========================================================
Private Function SafeGetModelType(ByVal m As Object) As Long
    On Error GoTo EH
    SafeGetModelType = m.Type
    Exit Function
EH:
    SafeGetModelType = -1
End Function

Private Function SafeGetIs3D(ByVal m As Object) As Variant
    On Error Resume Next
    Dim v As Variant

    Err.Clear
    v = CallByName(m, "Is3d", VbGet)
    If Err.Number = 0 Then
        SafeGetIs3D = CBool(v)
        Exit Function
    End If

    Err.Clear
    v = CallByName(m, "Is3D", VbGet)
    If Err.Number = 0 Then
        SafeGetIs3D = CBool(v)
        Exit Function
    End If

    SafeGetIs3D = Null
End Function

Private Function IsSheetModelName(ByVal modelName As String) As Boolean
    IsSheetModelName = (InStr(1, modelName, "[Sheet]", vbTextCompare) > 0)
End Function

Private Function CleanForLogicalName(ByVal s As String) As String
    Dim t As String
    t = s
    t = Replace(t, " ", "")
    t = Replace(t, "+", "_")
    t = Replace(t, "-", "NEG_")
    t = Replace(t, ".", "_")
    t = Replace(t, "[", "")
    t = Replace(t, "]", "")
    CleanForLogicalName = Left$(t, 60)
End Function

Private Function Q(ByVal s As String) As String
    s = Replace(s, """", "")
    Q = """" & s & """"
End Function


' =========================================================
' FILE PICKER (OpenRoads-safe; no Office; no CreateFileDialog)
' =========================================================
Private Function PickDgnFile(ByVal title As String) As String
    On Error GoTo EH

    Dim cd As Object
    Set cd = CreateObject("UserAccounts.CommonDialog")

    cd.Filter = "Design Files (*.dgn)|*.dgn|All Files (*.*)|*.*"
    cd.FilterIndex = 1
    cd.DialogTitle = title

    cd.ShowOpen
    If Len(cd.FileName) > 0 Then
        PickDgnFile = cd.FileName
    Else
        PickDgnFile = ""
    End If

    Exit Function

EH:
    ' Fallback for machines without that COM component
    PickDgnFile = InputBox(title & vbCrLf & vbCrLf & "Paste full path to the reference DGN:", "Reference DGN Path")
End Function
