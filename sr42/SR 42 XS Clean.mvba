Attribute VB_Name = "ModSR_42_XS_Clean"
Sub BmrSR_42_XS_Clean()
    Dim startPoint As Point3d
    Dim point As Point3d, point2 As Point3d
    Dim lngTemp As Long
    Dim oMessage As CadInputMessage

'   Send a keyin that can be a command string
    CadInputQueue.SendKeyin "OF=""Default"";SELVIEW 1"

    CadInputQueue.SendKeyin "OF=""XS_SHEET_MINOR_GRIDS"";SELVIEW 1"

    CadInputQueue.SendKeyin "OF=""XS_SHEET_MEDIUM_GRIDS"";SELVIEW 1"

    CadInputQueue.SendKeyin "OF=""XS_SHEET_MAJOR_GRIDS"";SELVIEW 1"

    CadInputQueue.SendKeyin "OF=""XS_SHEET_LABELS_STATION"";SELVIEW 1"

    CadInputQueue.SendKeyin "OF=""XS_SHEET_LABELS_OFFSET"";SELVIEW 1"

    CadInputQueue.SendKeyin "OF=""XS_SHEET_LABELS_ELEVATION"";SELVIEW 1"

    CadInputQueue.SendKeyin "OF=""XS_P_TX_FS_BS"";SELVIEW 1"

    CadInputQueue.SendKeyin "OF=""XS_P_SUBGRADE_GRANULAR"";SELVIEW 1"

    CadInputQueue.SendKeyin "OF=""XS_P_FINISHED_GRADE_ELEV_TX"";SELVIEW 1"

    CadInputQueue.SendKeyin "OF=""SHEET_BORDER"";SELVIEW 1"

    CadInputQueue.SendKeyin "OF=""Draft_XS_Volume_Annotation"";SELVIEW 1"

    CadInputQueue.SendKeyin "OF=""Draft_Named_Boundary"";SELVIEW 1"

    CadInputQueue.SendKeyin "OF=""Draft_Civil_Labels"";SELVIEW 1"

    CadInputQueue.SendKeyin "OF=""z - Construction"";SELVIEW 1"

    CadInputQueue.SendKeyin "OF=""XS_X_UNSUITABLE_MATERIAL"";SELVIEW 1"

    CadInputQueue.SendKeyin "OF=""XS_X_UNCLASS"";SELVIEW 1"

    CadInputQueue.SendKeyin "OF=""XS_X_TX"";SELVIEW 1"

    CadInputQueue.SendKeyin "ON=""XS_X_SHOULDER"";SELVIEW 1"

    CadInputQueue.SendKeyin "OF=""XS_X_ROW"";SELVIEW 1"

    CadInputQueue.SendKeyin "OF=""XS_X_PAVEMENT"";SELVIEW 1"

    CadInputQueue.SendKeyin "OF=""XS_X_MUCK"";SELVIEW 1"

    CadInputQueue.SendKeyin "OF=""XS_X_MERGE"";SELVIEW 1"

    CadInputQueue.SendKeyin "OF=""XS_X_GROUND_TX"";SELVIEW 1"

    CadInputQueue.SendKeyin "OF=""XS_X_FINAL"";SELVIEW 1"

    CadInputQueue.SendKeyin "ON=""XS_P_SUBGRADE_GRANULAR"";SELVIEW 1"

    CadInputQueue.SendKeyin "OF=""XS_X_GROUND"";SELVIEW 1"

'   Start a command
    CadInputQueue.SendCommand "DELETE ELEMENT"

    CadInputQueue.SendKeyin "ON=""Default"";SELVIEW 1"

    CadInputQueue.SendKeyin "ON=""XS_X_GROUND"";SELVIEW 1"

    CadInputQueue.SendKeyin "ON=""XS_SHEET_MINOR_GRIDS"";SELVIEW 1"

    CadInputQueue.SendKeyin "ON=""XS_SHEET_MEDIUM_GRIDS"";SELVIEW 1"

    CadInputQueue.SendKeyin "ON=""XS_SHEET_MAJOR_GRIDS"";SELVIEW 1"

    CadInputQueue.SendKeyin "ON=""XS_SHEET_LABELS_STATION"";SELVIEW 1"

    CadInputQueue.SendKeyin "ON=""XS_SHEET_LABELS_OFFSET"";SELVIEW 1"

    CadInputQueue.SendKeyin "ON=""XS_SHEET_LABELS_ELEVATION"";SELVIEW 1"

    CadInputQueue.SendKeyin "ON=""XS_P_TX_FS_BS"";SELVIEW 1"

    CadInputQueue.SendKeyin "ON=""XS_P_FINISHED_GRADE_ELEV_TX"";SELVIEW 1"

    CadInputQueue.SendKeyin "ON=""SHEET_BORDER"";SELVIEW 1"

    CadInputQueue.SendKeyin "ON=""Draft_XS_Volume_Annotation"";SELVIEW 1"

    CadInputQueue.SendKeyin "ON=""Draft_Named_Boundary"";SELVIEW 1"

    CadInputQueue.SendKeyin "ON=""Draft_Civil_Labels"";SELVIEW 1"

    CommandState.StartDefaultCommand
End Sub
