Attribute VB_Name = "Module1"
Sub BmrDel_title_BK_tx2()
    Dim startPoint As Point3d
    Dim point As Point3d, point2 As Point3d
    Dim lngTemp As Long
    Dim oMessage As CadInputMessage

'   Start a command
    CadInputQueue.SendCommand "LEVELMANAGER LEVEL OFFBYELEM"

'   Coordinates are in master units
    startPoint.X = 2.65764145010143
    startPoint.Y = 0.536336150683833
    startPoint.Z = 0#

'   Send a data point to the current command
    point.X = startPoint.X
    point.Y = startPoint.Y
    point.Z = startPoint.Z
    CadInputQueue.SendDataPoint point, 1

    point.X = startPoint.X + 0.131117420704136
    point.Y = startPoint.Y + 8.07122333399246E-03
    point.Z = startPoint.Z
    CadInputQueue.SendDataPoint point, 1

    CadInputQueue.SendCommand "DELETE ELEMENT"

'   Send a tentative point
    CadInputQueue.SendTentativePoint Point3dFromXYZ(2.67198592005881, 1.01522873516738, 0#), 1

    point.X = startPoint.X + 6.45021656523426E-03
    point.Y = startPoint.Y + 0.468496849248834
    point.Z = startPoint.Z
    CadInputQueue.SendAdjustedDataPoint point, 1

    CadInputQueue.SendTentativePoint Point3dFromXYZ(2.70635287933169, 1.01821807714293, 0#), 1

    point.X = startPoint.X + 4.23891054541223E-02
    point.Y = startPoint.Y + 0.468496849248834
    point.Z = startPoint.Z
    CadInputQueue.SendAdjustedDataPoint point, 1

    CadInputQueue.SendTentativePoint Point3dFromXYZ(2.73474297612233, 1.02120741911849, 0#), 1

    point.X = startPoint.X + 0.07832799434301
    point.Y = startPoint.Y + 0.468496849248834
    point.Z = startPoint.Z
    CadInputQueue.SendAdjustedDataPoint point, 1

    CadInputQueue.SendTentativePoint Point3dFromXYZ(2.76761571977465, 1.01223939319183, 0#), 1

    point.X = startPoint.X + 0.114266883231899
    point.Y = startPoint.Y + 0.468496849248834
    point.Z = startPoint.Z
    CadInputQueue.SendAdjustedDataPoint point, 1

    CadInputQueue.SendTentativePoint Point3dFromXYZ(2.72278925115785, 0.856793610463086, 0#), 1

    point.X = startPoint.X + 6.03585498985653E-02
    point.Y = startPoint.Y + 0.25343398817758
    point.Z = startPoint.Z
    CadInputQueue.SendAdjustedDataPoint point, 1

    CadInputQueue.SendTentativePoint Point3dFromXYZ(2.76313307291297, 0.828394861695335, 0#), 1

    point.X = startPoint.X + 0.109058549898566
    point.Y = startPoint.Y + 0.208871826015419
    point.Z = startPoint.Z
    CadInputQueue.SendAdjustedDataPoint point, 1

    CadInputQueue.SendTentativePoint Point3dFromXYZ(2.67945699816161, 0.819426835768677, 0#), 1

    point.X = startPoint.X + 1.16585498985664E-02
    point.Y = startPoint.Y + 0.218203100146692
    point.Z = startPoint.Z
    CadInputQueue.SendAdjustedDataPoint point, 1

    CadInputQueue.SendTentativePoint Point3dFromXYZ(2.67497435129993, 0.705831840697673, 0#), 1

    point.X = startPoint.X + 1.16585498985664E-02
    point.Y = startPoint.Y + 0.12185869860229
    point.Z = startPoint.Z
    CadInputQueue.SendAdjustedDataPoint point, 1

    CadInputQueue.SendTentativePoint Point3dFromXYZ(2.71531817305505, 0.698358485758791, 0#), 1

    point.X = startPoint.X + 6.03585498985653E-02
    point.Y = startPoint.Y + 0.121858698602291
    point.Z = startPoint.Z
    CadInputQueue.SendAdjustedDataPoint point, 1

    CadInputQueue.SendTentativePoint Point3dFromXYZ(2.77508679787744, 0.68640111785658, 0#), 1

    point.X = startPoint.X + 0.109058549898566
    point.Y = startPoint.Y + 0.121858698602291
    point.Z = startPoint.Z
    CadInputQueue.SendAdjustedDataPoint point, 1

'   Send a keyin that can be a command string
    CadInputQueue.SendKeyin "ON=""SHEET_TITLE_BLOCK"";SELVIEW 1"

    CadInputQueue.SendKeyin "ON=""SHEET_BORDER"";SELVIEW 1"

    CommandState.StartDefaultCommand
End Sub

Sub BmrCWsheetnopg()
    Dim startPoint As Point3d
    Dim point As Point3d, point2 As Point3d
    Dim lngTemp As Long
    Dim oMessage As CadInputMessage

'   Start a command
    CadInputQueue.SendCommand "TEXTEDITOR MODIFY"

'   Send a tentative point
'   Coordinates are in master units
    CadInputQueue.SendTentativePoint Point3dFromXYZ(2.71823604902004, 6.02459935202745E-02, 0#), 1

'   Send a reset to the current command
    CadInputQueue.SendReset

    CadInputQueue.SendTentativePoint Point3dFromXYZ(2.7191392684484, 0.058438982131489, 0#), 1

'   Coordinates are in master units
    startPoint.X = 2.71811666666668
    startPoint.Y = 5.76158761582048E-02
    startPoint.Z = 0#

'   Send a data point to the current command
    point.X = startPoint.X
    point.Y = startPoint.Y
    point.Z = startPoint.Z
    CadInputQueue.SendAdjustedDataPoint point, 1

'   XX-MacroComment_Header-XX

'   XX-MacroComment_KeyDownPerCharacter-XX

    CadInputQueue.SendCommand "TEXTEDITOR PLAYCOMMAND KEY_DOWN KEY_CODE 0x2C CONTROL_KEY_STATE DOWN SHIFT_KEY_STATE UP ALT_KEY_STATE UP"

'   XX-MacroComment_KeyDownPerCharacter-XX

    CadInputQueue.SendCommand "TEXTEDITOR PLAYCOMMAND KEY_DOWN KEY_CODE 0x20 CONTROL_KEY_STATE UP SHIFT_KEY_STATE UP ALT_KEY_STATE UP"

'   XX-MacroComment_InsertText-XX

'   Send a keyin that can be a command string
    CadInputQueue.SendKeyin "TEXTEDITOR PLAYCOMMAND INSERT_TEXT ""$PG$"""

    point.X = startPoint.X + 9.87415217965326E-03
    point.Y = startPoint.Y + 0.047263298665072
    point.Z = startPoint.Z
    CadInputQueue.SendDataPoint point, 1

    CommandState.StartDefaultCommand

End Sub

Sub AttachTitleBlockToSheets()

    Const REF_PATH As String = "PW_WORKDIR:d0300586\Title Block.dgn"
    Const REF_LOGICAL As String = "TITLEBLOCK"
    Const SHEET_NAME_PATTERN As String = "SR 32 -*"
    
    Dim oModel As ModelReference
    Dim oRef As Attachment
    Dim oAtt As Attachment
    Dim alreadyAttached As Boolean

    For Each oModel In ActiveDesignFile.Models
        
        If oModel.Type = msdModelTypeSheet Then
            
            If oModel.Name Like SHEET_NAME_PATTERN Then
                
                alreadyAttached = False
                For Each oAtt In oModel.Attachments
                    If UCase$(oAtt.LogicalName) = REF_LOGICAL Then
                        alreadyAttached = True
                        Exit For
                    End If
                Next oAtt
                
                If Not alreadyAttached Then
                    Set oRef = oModel.Attachments.AddCoincident(REF_PATH, "", REF_LOGICAL, "MDOT Title Block", True)
                End If
                
            End If
        End If
        
    Next oModel

End Sub

Sub BmrBRIDGE_NO_STAMP()
    Dim startPoint As Point3d
    Dim point As Point3d, point2 As Point3d
    Dim lngTemp As Long
    Dim oMessage As CadInputMessage

'   Start a command
    CadInputQueue.SendCommand "COPY ICON"

'   Send a tentative point
'   Coordinates are in master units
    CadInputQueue.SendTentativePoint Point3dFromXYZ(2.71888193378477, 5.32723941053352E-02, 0#), 1

'   Coordinates are in master units
    startPoint.X = 2.71811666666668
    startPoint.Y = 5.76158761582047E-02
    startPoint.Z = 0#

'   Send a data point to the current command
    point.X = startPoint.X
    point.Y = startPoint.Y
    point.Z = startPoint.Z
    CadInputQueue.SendAdjustedDataPoint point, 1

    point.X = startPoint.X - 1.34743454238701
    point.Y = startPoint.Y + 3.9616950344958E-03
    point.Z = startPoint.Z
    CadInputQueue.SendDataPoint point, 1

    CadInputQueue.SendCommand "MDL KEYIN PSELECT CHOOSE ELEMENT"

    CadInputQueue.SendCommand "TEXTEDITOR MODIFY"

    CadInputQueue.SendTentativePoint Point3dFromXYZ(1.36568416199386, 0.064244225683323, 0#), 1

    point.X = startPoint.X - 1.34743454238701
    point.Y = startPoint.Y + 3.96169503449586E-03
    point.Z = startPoint.Z
    CadInputQueue.SendAdjustedDataPoint point, 1

'   XX-MacroComment_Header-XX

'   XX-MacroComment_InsertText-XX

'   Send a keyin that can be a command string
    CadInputQueue.SendKeyin "TEXTEDITOR PLAYCOMMAND INSERT_TEXT ""**BRIG"""

'   XX-MacroComment_KeyDownPerCharacter-XX

    CadInputQueue.SendCommand "TEXTEDITOR PLAYCOMMAND KEY_DOWN KEY_CODE 0x02 CONTROL_KEY_STATE UP SHIFT_KEY_STATE UP ALT_KEY_STATE UP"

    CadInputQueue.SendKeyin "TEXTEDITOR PLAYCOMMAND INSERT_TEXT ""DGE 78.4**"""

    point.X = startPoint.X - 1.3254435083295
    point.Y = startPoint.Y + 3.82948716012608E-02
    point.Z = startPoint.Z
    CadInputQueue.SendDataPoint point, 1

    CommandState.StartDefaultCommand
End Sub



Sub XS_Master_AllSheets()

    Dim oModel As ModelReference

    ' Loop through all models in the active DGN
    For Each oModel In ActiveDesignFile.Models

        ' Only run on sheet models
        If oModel.Type = msdModelTypeSheet Then

            oModel.Activate   ' make this sheet active

            ' Call the recorded macro that does the delete on this sheet
            BmrDel_title_BK_tx2
            BmrCWsheetnopg
            BmrBRIDGE_NO_STAMP
            AttachTitleBlockToSheets

        End If

    Next oModel

    ' Save settings after all changes
    CadInputQueue.SendCommand "FILEDESIGN SAVESETTINGS"

   
End Sub
