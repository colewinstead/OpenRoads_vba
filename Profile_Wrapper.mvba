Attribute VB_Name = "Module1"
Sub Wrapper_AllProfiles()

    Dim oModel As ModelReference

    ' Loop through all models in the active DGN
    For Each oModel In ActiveDesignFile.Models

        ' Only run on profile models
        If InStr(1, oModel.Name, "profile", vbTextCompare) > 0 Then

            oModel.Activate   ' make this profile model active

            ' Call the recorded macro that does the delete/change on this profile
            BmrISD_WK_SH_SR_8

        End If

    Next oModel

    ' Save settings after all changes
    CadInputQueue.SendCommand "FILEDESIGN SAVESETTINGS"

    MsgBox "Finished changing all profile models.", vbInformation

End Sub
