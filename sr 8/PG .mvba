Attribute VB_Name = "ModPG_"
Sub BmrPG_()
    Dim startPoint As Point3d
    Dim point As Point3d, point2 As Point3d
    Dim lngTemp As Long
    Dim oMessage As CadInputMessage

'   Start a command
    CadInputQueue.SendCommand "COPY ICON"

'   Send a tentative point
'   Coordinates are in master units
    CadInputQueue.SendTentativePoint Point3dFromXYZ(2.71924439061489, 5.89950527198434E-02, 0#), 1

'   Coordinates are in master units
    startPoint.X = 2.71811666666668
    startPoint.Y = 5.76158761582048E-02
    startPoint.Z = 0#

'   Send a data point to the current command
    point.X = startPoint.X
    point.Y = startPoint.Y
    point.Z = startPoint.Z
    CadInputQueue.SendAdjustedDataPoint point, 1

    point.X = startPoint.X + 3.31527639207057E-02
    point.Y = startPoint.Y + 4.86511849917313E-02
    point.Z = startPoint.Z
    CadInputQueue.SendDataPoint point, 1

    point.X = startPoint.X + 0.021458370583809
    point.Y = startPoint.Y + 0.080757952980139
    point.Z = startPoint.Z
    CadInputQueue.SendDataPoint point, 1

    CommandState.StartDefaultCommand
End Sub
Sub Wrapper_AllSheets()

    Dim oModel As ModelReference

    ' Loop through all models in the active DGN
    For Each oModel In ActiveDesignFile.Models

        ' Only run on sheet models
        If oMode = msdModelTypeSheet Then

            oModel.Activate   ' make this sheet active

            ' Call the recorded macro that does the delete on this sheet
            BmrPG_

        End If

    Next oModel

    ' Save settings after all changes
    CadInputQueue.SendCommand "FILEDESIGN SAVESETTINGS"

    MsgBox "Finished changing the title on all sheet models.", vbInformation

End Sub
