Attribute VB_Name = "ContourPlotterMain"
Option Explicit
' SPDX-License-Identifier: MIT
Public CPModel As ModelReference
Public CPFileName As String, CPModelName As String, CPUnitName As String, CPGcsName As String
Public CPUOR As Double, CPCancelled As Boolean, CPBusy As Boolean
Public Const CP_APP As String = "OpenRoadsContourPlotter"

Public Sub Main()
    On Error GoTo Failed
    CPRequire Not CPBusy, "Contour Plotter is already processing."
    CPCancelled = False
    Set CPModel = ActiveModelReference
    CPFileName = ActiveDesignFile.FullName
    CPModelName = CPModel.name
    CPUnitName = CPWorkingUnit()
    CPGcsName = CPDetectedGCS()
    CPUOR = CPModel.UORsPerMasterUnit
    CPPreflight
    Load frmContourPlotter
    frmContourPlotter.Show vbModal
    Exit Sub
Failed:
    MsgBox Err.Description, vbExclamation, "Contour Plotter"
End Sub

Public Sub CPRequire(ByVal condition As Boolean, ByVal message As String)
    If Not condition Then Err.Raise vbObjectError + 2810, "Contour Plotter", message
End Sub

Public Function CPWorkingUnit() As String
    Dim unit As MeasurementUnit, metres As Double
    unit = ActiveModelReference.MasterUnit
    CPRequire unit.Base = msdMeasurementBaseMeter, "Model master units must be linear."
    CPRequire unit.UnitsPerBaseNumerator > 0 And unit.UnitsPerBaseDenominator > 0, "Invalid model unit ratio."
    metres = unit.UnitsPerBaseDenominator / unit.UnitsPerBaseNumerator
    If Abs(metres - 1#) < 0.000000000001 Then CPWorkingUnit = "m"
    If Abs(metres - 0.3048) < 0.000000000001 Then CPWorkingUnit = "ft"
    If Abs(metres - 1200# / 3937#) < 0.000000000001 Then CPWorkingUnit = "us-ft"
    CPRequire Len(CPWorkingUnit) > 0, "Supported master units: metre, international foot, US survey foot."
End Function

Public Function CPDetectedGCS() As String
    Dim gcs As GeographicCoordinateSystem
    On Error GoTo Unknown
    Set gcs = ActiveModelReference.GetGCS(True)
    If gcs Is Nothing Then GoTo Unknown
    CPDetectedGCS = gcs.name & " | " & gcs.DatumName & " | " & gcs.VerticalDatumName & " | " & gcs.Units
    Exit Function
Unknown:
    CPDetectedGCS = "(No readable DGN GCS; explicitly confirm the local grid.)"
End Function

Public Sub CPPreflight()
    CPRequire Not CPModel Is Nothing, "Run ContourPlotterMain.Main first."
    CPRequire CPModel.IsActive, "The active model changed; restart Contour Plotter."
    CPRequire ActiveDesignFile.FullName = CPFileName And ActiveModelReference.name = CPModelName, "DGN/model changed."
    CPRequire Not CPModel.IsAttachment, "Reference models are not output targets."
    CPRequire CPModel.Type = msdModelTypeNormal, "Use a design model; sheet/drawing models are rejected."
    CPRequire Not CPModel.IsReadOnly And Not CPModel.IsLocked, "The active model is read-only or locked."
    CPRequire CPWorkingUnit() = CPUnitName And CPModel.UORsPerMasterUnit = CPUOR, "Model working units/resolution changed."
    CPRequire CPDetectedGCS() = CPGcsName, "Model GCS changed while processing."
    CPRequire Not CPCancelled, "Cancelled."
End Sub

Public Function CPNumber(ByVal Number As Double) As String
    CPNumber = Trim$(Str$(Number))
    If Left$(CPNumber, 1) = "." Then CPNumber = "0" & CPNumber
    If Left$(CPNumber, 2) = "-." Then CPNumber = "-0" & Mid$(CPNumber, 2)
End Function

Public Function CPJson(ByVal value As String) As String
    Dim i As Long, c As Long, result As String
    result = Chr$(34)
    For i = 1 To Len(value)
        c = AscW(Mid$(value, i, 1)) And &HFFFF&
        Select Case c
            Case 34: result = result & "\" & Chr$(34)
            Case 92: result = result & "\\"
            Case 32 To 126: result = result & ChrW$(c)
            Case Else: result = result & "\u" & Right$("0000" & Hex$(c), 4)
        End Select
    Next i
    CPJson = result & Chr$(34)
End Function

Public Function CPReadUnicode(ByVal filename As String) As String
    Dim stream As Object
    Set stream = CreateObject("Scripting.FileSystemObject").OpenTextFile(filename, 1, False, -1)
    CPReadUnicode = stream.ReadAll
    stream.Close
End Function

Public Sub CPStatus(ByVal message As String)
    frmContourPlotter.SetStatus message
    DoEvents
End Sub

Attribute VB_Name = "frmContourPlotter"
Attribute VB_Base = "0{F6D44C04-BD3C-47EB-AE11-EACFD04F7238}{97AF7AD4-6A1F-41E2-BE73-675BC620CD77}"
Attribute VB_GlobalNameSpace = False
Attribute VB_Creatable = False
Attribute VB_PredeclaredId = True
Attribute VB_Exposed = False
Attribute VB_TemplateDerived = False
Attribute VB_Customizable = False
Option Explicit
' SPDX-License-Identifier: MIT
' Paste into a NEW blank UserForm named frmContourPlotter.
Private mControls As Object, mSurfaceNames As Collection
Private WithEvents cmdBrowse As MSForms.CommandButton
Attribute cmdBrowse.VB_VarHelpID = -1
Private WithEvents cmdEngine As MSForms.CommandButton
Attribute cmdEngine.VB_VarHelpID = -1
Private WithEvents cmdInspect As MSForms.CommandButton
Attribute cmdInspect.VB_VarHelpID = -1
Private WithEvents cmdPreview As MSForms.CommandButton
Attribute cmdPreview.VB_VarHelpID = -1
Private WithEvents cmdGenerate As MSForms.CommandButton
Attribute cmdGenerate.VB_VarHelpID = -1
Private WithEvents cmdRegenerate As MSForms.CommandButton
Attribute cmdRegenerate.VB_VarHelpID = -1
Private WithEvents cmdCancel As MSForms.CommandButton
Attribute cmdCancel.VB_VarHelpID = -1
Private WithEvents cmdPrevious As MSForms.CommandButton
Attribute cmdPrevious.VB_VarHelpID = -1
Private WithEvents chkByLevel As MSForms.CheckBox
Attribute chkByLevel.VB_VarHelpID = -1
Private mInspectedSource As String

Private Function AddControl(parent As Object, ByVal kind As String, ByVal name As String, _
        ByVal x As Single, ByVal y As Single, ByVal width As Single, ByVal height As Single) As Object
    Dim c As Object
    Set c = parent.Controls.Add("Forms." & kind & ".1", name, True)
    c.Left = x: c.Top = y: c.width = width: c.height = height
    mControls.Add name, c
    Set AddControl = c
End Function

Private Sub Label(parent As Object, ByVal name As String, ByVal value As String, _
        ByVal x As Single, ByVal y As Single, ByVal width As Single, Optional ByVal height As Single = 20)
    Dim c As Object
    Set c = AddControl(parent, "Label", name, x, y, width, height)
    c.caption = value
End Sub

Private Function TextBox(parent As Object, ByVal name As String, ByVal caption As String, _
        ByVal y As Single, ByVal value As String, Optional ByVal width As Single = 450) As Object
    Label parent, "lbl" & name, caption, 18, y + 3, 190
    Set TextBox = AddControl(parent, "TextBox", name, 220, y, width, 22)
    TextBox.value = value
End Function

Private Function Combo(parent As Object, ByVal name As String, ByVal caption As String, _
        ByVal y As Single, ByVal values As String) As MSForms.ComboBox
    Dim c As MSForms.ComboBox, item As Variant
    Label parent, "lbl" & name, caption, 18, y + 3, 190
    Set c = AddControl(parent, "ComboBox", name, 220, y, 450, 22)
    c.style = fmStyleDropDownList
    If Len(values) > 0 Then
        For Each item In Split(values, "|")
            c.AddItem CStr(item)
        Next item
    End If
    Set Combo = c
End Function

Private Function Button(parent As Object, ByVal name As String, ByVal caption As String, _
        ByVal x As Single, ByVal y As Single, ByVal width As Single) As MSForms.CommandButton
    Set Button = AddControl(parent, "CommandButton", name, x, y, width, 27)
    Button.caption = caption
End Function

Private Function Check(parent As Object, ByVal name As String, ByVal caption As String, _
        ByVal y As Single, ByVal initial As Boolean) As MSForms.CheckBox
    Set Check = AddControl(parent, "CheckBox", name, 18, y, 650, 24)
    Check.caption = caption: Check.value = initial
End Function

Private Sub UserForm_Initialize()
    Dim pages As MSForms.MultiPage, p As Object, c As Object
    Set mControls = CreateObject("Scripting.Dictionary")
    Set mSurfaceNames = New Collection
    Me.caption = "Contour Plotter | OpenRoads Designer"
    Me.width = 742: Me.height = 644
    Me.StartUpPosition = 1
    Me.Font.name = "Segoe UI": Me.Font.size = 10
    Label Me, "heading", "CONTOUR PLOTTER", 18, 14, 688, 25
    mControls("heading").Font.Bold = True: mControls("heading").Font.size = 14
    Label Me, "target", CPFileName & vbCrLf & "Model: " & CPModelName & " | master units: " & CPUnitName, 18, 44, 688, 38
    Set pages = AddControl(Me, "MultiPage", "pages", 12, 90, 708, 432)
    Do While pages.pages.Count < 3
        pages.pages.Add
    Loop
    pages.pages(0).caption = "1  Source and coordinates"
    pages.pages(1).caption = "2  Contours and labels"
    pages.pages(2).caption = "3  MDOT levels and output"
    Set p = pages.pages(0)
    Set c = TextBox(p, "source", "Merged terrain LandXML", 18, "", 338)
    Set cmdBrowse = Button(p, "browse", "Browse...", 566, 16, 104)
    Set c = TextBox(p, "engine", "ContourPlotter.exe", 50, GetSetting(CP_APP, "Settings", "Engine", ""), 338)
    Set cmdEngine = Button(p, "engineBrowse", "Browse...", 566, 48, 104)
    Set c = Combo(p, "surface", "Source surface", 88, "")
    Set cmdInspect = Button(p, "inspect", "Inspect LandXML", 220, 121, 160)
    Label p, "sourceStats", "Export the already merged terrain to LandXML in ORD. Native terrain export is manual in this version.", 18, 157, 652, 38
    Set c = Combo(p, "axis", "Stored point axis order", 202, "E N Z (xy)|N E Z (ne)")
    Set c = Combo(p, "horizontal", "Source horizontal unit", 232, "m|ft|us-ft")
    Set c = Combo(p, "vertical", "Source vertical unit", 262, "m|ft|us-ft")
    Set c = TextBox(p, "crs", "Verified CRS / local grid", 292, "")
    Set c = TextBox(p, "datum", "Verified vertical datum", 322, "")
    Label p, "gcs", CPGcsName & vbCrLf & "ft = international foot; us-ft = US survey foot. No reprojection or datum conversion.", 18, 354, 652, 40

    Set p = pages.pages(1)
    Set c = TextBox(p, "minor", "Minor interval (source Z unit)", 18, "1")
    Set c = TextBox(p, "major", "Major interval (source Z unit)", 48, "5")
    Set c = TextBox(p, "base", "Contour base elevation", 78, "0")
    Set c = Combo(p, "labels", "Automatic labels", 108, "Major only|Major and minor|None")
    c.ListIndex = 0
    Set c = TextBox(p, "spacing", "Label spacing (model units)", 138, "250")
    Set c = TextBox(p, "scale", "Model units per paper inch", 168, "50")
    Set c = TextBox(p, "paperMajor", "Major label height (paper in)", 198, "0.10", 160)
    Label p, "lblPaperMinor", "Minor (in)", 396, 201, 80
    Set c = AddControl(p, "TextBox", "paperMinor", 486, 198, 184, 22)
    c.value = "0.10"
    Set c = TextBox(p, "clearance", "Paper gap clearance (inches)", 228, "0.02")
    Set c = Combo(p, "dimension", "Geometry dimension", 258, "2D (Z = 0)|3D (contour elevation)")
    c.ListIndex = 0
    Set c = TextBox(p, "maxLabels", "Maximum labels per path", 288, "100")
    Set c = Check(p, "gaps", "Break contour under elevation labels", 322, True)
    Label p, "scaleHelp", "Example: 0.10 in x 50 ft/in = 5 ft model text height. For a metric 1:500 plot, enter 12.7 m/in. Smoothing is disabled. Short fragments are reported, never removed.", 18, 354, 652, 40

    Set p = pages.pages(2)
    Set c = Combo(p, "majorLevel", "Major contour level", 18, ""): CPFillLevels c, "majorLevel"
    Set c = Combo(p, "minorLevel", "Minor contour level", 48, ""): CPFillLevels c, "minorLevel"
    Set c = Combo(p, "majorLabel", "Major label level", 78, ""): CPFillLevels c, "majorLabel"
    Set c = Combo(p, "minorLabel", "Minor label level", 108, ""): CPFillLevels c, "minorLabel"
    Set c = Combo(p, "style", "DGN / library text style", 138, ""): CPFillStyles c
    Set chkByLevel = Check(p, "byLevel", "Use Existing Level Symbology", 173, True)
    Set c = TextBox(p, "color", "Override color (0-255)", 207, "0")
    Set c = TextBox(p, "weight", "Override weight (0-31)", 237, "0")
    Set c = TextBox(p, "lineStyle", "Override line style name", 267, "")
    Set c = TextBox(p, "previous", "Previous run journal (.cpj)", 305, _
        GetSetting(CP_APP, "LastRuns", CPFileName & "|" & CPModelName, ""), 338)
    Set cmdPrevious = Button(p, "previousBrowse", "Browse...", 566, 303, 104)
    Label p, "stagedHelp", "Regenerate stages a complete replacement, then asks before deleting recorded prior members, including manual edits. Keep both run folders until the DGN is saved and checked.", 18, 345, 652, 48
    EnableOverrides
    Label Me, "status", "Inspect the LandXML, verify coordinates, then choose existing levels and a text style.", 18, 532, 688, 36
    Set cmdPreview = Button(Me, "preview", "Analyze / Preview", 18, 575, 156)
    Set cmdGenerate = Button(Me, "generate", "Generate", 344, 575, 120)
    Set cmdRegenerate = Button(Me, "regenerate", "Regenerate", 474, 575, 120)
    Set cmdCancel = Button(Me, "cancel", "Close", 604, 575, 102)
    cmdCancel.Cancel = True
End Sub

Public Sub SetStatus(ByVal message As String)
    mControls("status").caption = message
    Me.Repaint
End Sub

Private Sub EnableOverrides()
    Dim name As Variant
    For Each name In Array("color", "weight", "lineStyle")
        mControls(name).Enabled = Not chkByLevel.value
    Next name
End Sub

Private Sub chkByLevel_Click()
    If Not mControls Is Nothing Then EnableOverrides
End Sub

Private Sub cmdEngine_Click()
    Dim value As String
    value = CPBrowse("Select packaged ContourPlotter.exe", CStr(mControls("engine").value), "Contour engine (*.exe)|*.exe|All files (*.*)|*.*")
    If Len(value) > 0 Then
        mControls("engine").value = value
        SaveSetting CP_APP, "Settings", "Engine", value
    End If
End Sub

Private Sub cmdBrowse_Click()
    Dim value As String
    value = CPBrowse("Select already merged terrain LandXML", CStr(mControls("source").value), "LandXML files (*.xml)|*.xml|All files (*.*)|*.*")
    If Len(value) > 0 Then mControls("source").value = value
End Sub

Private Sub cmdPrevious_Click()
    Dim value As String
    value = CPBrowse("Select prior elements.cpj from its run folder", CStr(mControls("previous").value), "Contour journals (*.cpj)|*.cpj|All files (*.*)|*.*")
    If Len(value) > 0 Then mControls("previous").value = value
End Sub

Private Sub Busy(ByVal value As Boolean)
    Dim name As Variant
    CPBusy = value
    For Each name In mControls.keys
        If name <> "cancel" And name <> "status" Then mControls(name).Enabled = Not value
    Next name
    If value Then cmdCancel.caption = "Cancel" Else cmdCancel.caption = "Close"
    If Not value Then EnableOverrides
End Sub

Private Sub cmdInspect_Click()
    Dim runID As String, job As String, lines As Variant, row As Variant, i As Long, message As String
    On Error GoTo Failed
    If CPBusy Then Exit Sub
    CPCancelled = False: Busy True
    CPPreflight
    mControls("source").value = CPPath(CStr(mControls("source").value))
    runID = CPNewRunID(): job = CPNewJob(runID)
    CPStatus "Inspecting source surfaces and declared metadata..."
    CPRunEngine CStr(mControls("engine").value), job, CPRequest("inspect", runID, job, CStr(mControls("source").value), "{}", "{}")
    lines = Split(Replace(CPReadUnicode(job & "\surfaces.tsv"), vbCr, ""), vbLf)
    row = Split(CStr(lines(0)), vbTab)
    CPRequire UBound(row) = 3, "Invalid surface inventory."
    CPRequire row(0) = "INSPECT1", "Invalid inspection version."
    SetUnit "horizontal", CStr(row(1))
    SetUnit "vertical", CStr(row(2))
    mControls("crs").value = row(3)
    mControls("surface").Clear
    Set mSurfaceNames = New Collection
    For i = 1 To UBound(lines)
        If Len(lines(i)) > 0 Then
            row = Split(CStr(lines(i)), vbTab)
            CPRequire UBound(row) = 3, "Invalid surface inventory row."
            mSurfaceNames.Add CStr(row(1))
            mControls("surface").AddItem row(1) & " | " & row(2) & " points, " & row(3) & " faces"
        End If
    Next i
    If mSurfaceNames.Count = 1 Then mControls("surface").ListIndex = 0
    mInspectedSource = CPPath(CStr(mControls("source").value))
    SetStatus "Choose a surface and resolve axis order, units, CRS and vertical datum. Face counts include invisible source faces until analysis."
    Busy False
    Exit Sub
Failed:
    message = Err.Description
    Busy False
    SetStatus message
    MsgBox message, vbExclamation, "Contour Plotter"
End Sub

Private Sub SetUnit(ByVal name As String, ByVal value As String)
    Dim unit As String, i As Long
    Select Case value
        Case "meter", "metre": unit = "m"
        Case "foot", "internationalFoot": unit = "ft"
        Case "USSurveyFoot": unit = "us-ft"
    End Select
    mControls(name).ListIndex = -1
    For i = 0 To mControls(name).ListCount - 1
        If mControls(name).List(i) = unit Then mControls(name).ListIndex = i
    Next i
End Sub

Private Function Number(ByVal name As String) As Double
    Dim value As String
    value = Trim$(CStr(mControls(name).value))
    CPRequire Len(value) > 0 And IsNumeric(value), "Enter a valid number for " & name & "."
    Number = CDbl(value)
    CPRequire Abs(Number) <= 1000000000#, "Input exceeds the safety range: " & name
End Function

Private Function Spatial() As String
    Dim index As Long, axis As String
    CPRequire CPPath(CStr(mControls("source").value)) = mInspectedSource And Len(mInspectedSource) > 0, "Inspect this LandXML before proceeding."
    index = mControls("surface").ListIndex
    CPRequire index >= 0 And index < mSurfaceNames.Count, "Select the named LandXML surface."
    CPRequire mControls("axis").ListIndex >= 0, "Explicitly select stored axis order."
    If mControls("axis").ListIndex = 0 Then axis = "xy" Else axis = "ne"
    CPRequire mControls("horizontal").ListIndex >= 0 And mControls("vertical").ListIndex >= 0, "Resolve horizontal and vertical units."
    CPRequire Len(Trim$(CStr(mControls("crs").value))) > 0, "Enter a verified CRS/local grid."
    CPRequire Len(Trim$(CStr(mControls("datum").value))) > 0, "Enter a verified vertical datum."
    Spatial = "{""surface_index"":" & CStr(index) & ",""surface_name"":" & CPJson(CStr(mSurfaceNames(index + 1))) & _
        ",""axis_order"":" & CPJson(axis) & ",""horizontal_unit"":" & CPJson(CStr(mControls("horizontal").value)) & _
        ",""vertical_unit"":" & CPJson(CStr(mControls("vertical").value)) & ",""model_unit"":" & CPJson(CPUnitName) & _
        ",""crs"":" & CPJson(CStr(mControls("crs").value)) & ",""vertical_datum"":" & CPJson(CStr(mControls("datum").value)) & "}"
End Function

Private Function Settings(ByVal widths As String, ByVal boxHeight As Double, ByVal minorBoxHeight As Double) As String
    Dim mode As String, gaps As String, maxLabels As Double
    Select Case mControls("labels").ListIndex
        Case 0: mode = "major"
        Case 1: mode = "both"
        Case 2: mode = "none"
        Case Else: CPRequire False, "Select the label mode."
    End Select
    If mControls("gaps").value Then gaps = "true" Else gaps = "false"
    maxLabels = Number("maxLabels")
    CPRequire maxLabels = Fix(maxLabels) And maxLabels >= 1 And maxLabels <= 10000, "Maximum labels must be an integer in 1..10000."
    Settings = "{""minor"":" & CPNumber(Number("minor")) & ",""major"":" & CPNumber(Number("major")) & _
        ",""base"":" & CPNumber(Number("base")) & ",""label_mode"":" & CPJson(mode) & _
        ",""label_spacing"":" & CPNumber(Number("spacing")) & ",""paper_height_major"":" & CPNumber(Number("paperMajor")) & _
        ",""paper_height_minor"":" & CPNumber(Number("paperMinor")) & _
        ",""scale"":" & CPNumber(Number("scale")) & ",""clearance_paper"":" & CPNumber(Number("clearance")) & _
        ",""dimension"":" & CStr(mControls("dimension").ListIndex + 2) & ",""break_lines"":" & gaps & _
        ",""max_labels"":" & CStr(CLng(maxLabels)) & ",""text_widths"":" & widths
    If boxHeight > 0 Then Settings = Settings & ",""text_box_height"":" & CPNumber(boxHeight)
    If minorBoxHeight > 0 Then Settings = Settings & ",""text_box_height_minor"":" & CPNumber(minorBoxHeight)
    Settings = Settings & "}"
End Function

Private Sub cmdPreview_Click()
    Workflow False, False
End Sub

Private Sub cmdGenerate_Click()
    Workflow True, False
End Sub

Private Sub cmdRegenerate_Click()
    Workflow True, True
End Sub

Private Sub Workflow(ByVal insert As Boolean, ByVal regenerate As Boolean)
    Dim runID As String, job As String, spatialJSON As String, settingsJSON As String, request As String
    Dim analysis As Variant, widths As String, boxHeight As Double, height As Double, minorHeight As Double, minorBoxHeight As Double
    Dim prior As String, message As String, color As Long, weight As Long, item As Variant
    Dim level As level, style As TextStyle, h As Integer, header As String, fields As Variant
    On Error GoTo Failed
    If CPBusy Then Exit Sub
    CPCancelled = False
    CPPreflight
    spatialJSON = Spatial()
    settingsJSON = Settings("{}", 0#, 0#)
    If regenerate Then
        prior = CPPath(CStr(mControls("previous").value))
        CPRequire CreateObject("Scripting.FileSystemObject").FileExists(prior), "Select a previous committed elements.cpj."
    End If
    Busy True
    runID = CPNewRunID(): job = CPNewJob(runID)
    CPStatus "Analyzing source triangles and contour elevations..."
    CPRunEngine CStr(mControls("engine").value), job, CPRequest("analyze", runID, job, CStr(mControls("source").value), spatialJSON, settingsJSON)
    analysis = Split(Replace(Replace(CPReadUnicode(job & "\analysis.tsv"), vbCr, ""), vbLf, ""), vbTab)
    CPRequire UBound(analysis) = 13, "Invalid analysis metadata."
    height = CPParseNumber(CStr(analysis(10))): minorHeight = CPParseNumber(CStr(analysis(11)))
    mControls("sourceStats").caption = CStr(analysis(0)) & " | " & CStr(analysis(1)) & " points | " & _
        CStr(analysis(2)) & " visible faces | Z " & CStr(analysis(3)) & " to " & CStr(analysis(4)) & " " & CStr(analysis(12))
    widths = "{}": boxHeight = height: minorBoxHeight = minorHeight
    If mControls("labels").ListIndex <> 2 Then
        CPStatus "Measuring elevation strings with the selected DGN text style..."
        widths = CPMeasuredWidths(job, CStr(mControls("style").value), height, minorHeight, boxHeight, minorBoxHeight)
    End If
    settingsJSON = Settings(widths, boxHeight, minorBoxHeight)
    request = CPRequest("generate", runID, job, CStr(mControls("source").value), spatialJSON, settingsJSON)
    request = Left$(request, Len(request) - 1) & ",""expected_source_sha256"":" & CPJson(CStr(analysis(13))) & "}"
    CPStatus "Generating connected contours, labels and physical gaps..."
    CPRunEngine CStr(mControls("engine").value), job, request
    CPPreflight
    h = FreeFile
    Open job & "\geometry.cp2" For Input Access Read Lock Write As #h
    Line Input #h, header
    Close #h: h = 0
    fields = Split(header, vbTab)
    CPRequire UBound(fields) = 13, "Invalid output header."
    If Not insert Then
        SetStatus "Preview: " & CStr(fields(4)) & " native line strings; " & CStr(fields(5)) & " labels. No DGN writes. " & job
        Busy False
        Exit Sub
    End If
    Set level = CPLevel(CStr(mControls("majorLevel").value))
    Set level = CPLevel(CStr(mControls("minorLevel").value))
    If mControls("labels").ListIndex <> 2 Then Set level = CPLevel(CStr(mControls("majorLabel").value))
    If mControls("labels").ListIndex = 1 Then Set level = CPLevel(CStr(mControls("minorLabel").value))
    If Not chkByLevel.value Then
        CPRequire Number("color") = Fix(Number("color")) And Number("weight") = Fix(Number("weight")), "Overrides must be integers."
        color = CLng(Number("color")): weight = CLng(Number("weight"))
    End If
    message = CPImport(job & "\geometry.cp2", job, runID, CStr(mControls("majorLevel").value), _
        CStr(mControls("minorLevel").value), CStr(mControls("majorLabel").value), CStr(mControls("minorLabel").value), _
        CStr(mControls("style").value), height, minorHeight, boxHeight, minorBoxHeight, CBool(chkByLevel.value), color, weight, CStr(mControls("lineStyle").value), _
        "Declared source CRS: " & CStr(analysis(5)) & vbCrLf & "Confirmed grid: " & CStr(mControls("crs").value) & _
        vbCrLf & "Vertical datum: " & CStr(mControls("datum").value) & " | Axis: " & CStr(mControls("axis").value), CLng(mControls("dimension").ListIndex + 2))
    SaveSetting CP_APP, "Settings", "Engine", CStr(mControls("engine").value)
    SaveSetting CP_APP, "Settings", "TextStyle", CStr(mControls("style").value)
    For Each item In Array("majorLevel", "minorLevel", "majorLabel", "minorLabel")
        SaveSetting CP_APP, "Levels", CStr(item), CStr(mControls(item).value)
    Next item
    SaveSetting CP_APP, "LastRuns", CPFileName & "|" & CPModelName, job & "\elements.cpj"
    mControls("previous").value = job & "\elements.cpj"
    SetStatus message
    If regenerate Then CPRemovePrevious prior
    Busy False
    MsgBox message, vbInformation, "Contour Plotter"
    Exit Sub
Failed:
    message = Err.Description
    On Error Resume Next
    If h <> 0 Then Close #h
    On Error GoTo 0
    Busy False
    SetStatus message
    MsgBox message, vbExclamation, "Contour Plotter"
End Sub

Private Sub cmdCancel_Click()
    If CPBusy Then
        CPCancelled = True
        SetStatus "Cancellation requested..."
    Else
        Unload Me
    End If
End Sub

Private Sub UserForm_QueryClose(Cancel As Integer, CloseMode As Integer)
    If CPBusy Then
        CPCancelled = True
        Cancel = True
    End If
End Sub

Attribute VB_Name = "modContourElements"
Option Explicit
' SPDX-License-Identifier: MIT
Public Const CP_XDATA As String = "OpenRoadsContourPlotter_v1"

Public Sub CPTag(element As element, ByVal runID As String)
    Dim data(0 To 0) As XDatum
    data(0).Type = msdXDatumTypeString
    data(0).value = "CP1|" & runID
    element.SetXData CP_XDATA, data
End Sub

Public Function CPTagValue(element As element) As String
    Dim data() As XDatum
    On Error GoTo missing
    If Not element.HasXData(CP_XDATA) Then Exit Function
    data = element.GetXData(CP_XDATA)
    If UBound(data) >= 0 Then
        If data(0).Type = msdXDatumTypeString Then CPTagValue = CStr(data(0).value)
    End If
missing:
End Function

Public Sub CPApply(element As element, level As level, ByVal useByLevel As Boolean, _
        ByVal color As Long, ByVal weight As Long, ByVal styleName As String)
    Dim style As LineStyle
    ' Bentley's Level object assignment follows AddElement, as in the existing tool.
    Set element.level = level
    If useByLevel Then
        element.color = ByLevelColor
        element.LineWeight = ByLevelLineWeight
        Set element.LineStyle = ByLevelLineStyle
    Else
        CPRequire color >= 0 And color <= 255 And weight >= 0 And weight <= 31, "Invalid element color/weight override."
        Set style = ActiveDesignFile.LineStyles.item(styleName)
        CPRequire Not style Is Nothing, "Line style override unavailable."
        element.color = color
        element.LineWeight = weight
        Set element.LineStyle = style
    End If
    element.Class = msdElementClassPrimary
    element.GraphicGroup = 0
    element.Rewrite
    CPRequire element.level.name = level.name, "Level assignment did not survive Rewrite."
    If useByLevel Then
        CPRequire element.color = ByLevelColor And element.LineWeight = ByLevelLineWeight, "ByLevel color/weight did not survive Rewrite."
        CPRequire element.LineStyle.name = ByLevelLineStyle.name, "ByLevel line style did not survive Rewrite."
    End If
End Sub

Public Sub CPStartJournal(ByVal filename As String, ByVal runID As String, ByRef journal As Object)
    Dim fso As Object
    Set fso = CreateObject("Scripting.FileSystemObject")
    CPRequire Not fso.FileExists(filename), "Insertion journal already exists."
    CPRequire InStr(CPFileName & CPModelName, vbTab) = 0, "DGN/model names containing tabs are unsupported."
    Set journal = fso.CreateTextFile(filename, False, True)
    journal.WriteLine "CPJ1" & vbTab & runID
    journal.WriteLine CPFileName
    journal.WriteLine CPModelName
    journal.WriteLine CPNumber(CDbl(ActiveDesignFile.DateCreated))
    journal.Close
    Set journal = fso.OpenTextFile(filename, 8, False, -1)
End Sub

Public Function CPRollback(ByVal added As Collection, ByVal runID As String) As Long
    Dim i As Long, element As element
    On Error Resume Next
    For i = added.Count To 1 Step -1
        Err.Clear
        Set element = added(i)
        If DLongToString(element.id) <> "0" Then
            If CPTagValue(element) = "CP1|" & runID Then
                CPModel.RemoveElement element
            Else
                Err.Raise vbObjectError + 2813, , "New element lost its run tag."
            End If
        End If
        If Err.Number <> 0 Then CPRollback = CPRollback + 1
    Next i
    On Error GoTo 0
End Function

Public Sub CPRemovePrevious(ByVal filename As String)
    Dim stream As Object, fso As Object, header As Variant, row As Variant, line As String
    Dim ids As New Collection, stamps As New Collection, runID As String, element As element
    Dim i As Long, changed As Long, missing As Long, removed As Long, lastLine As String, message As String
    On Error GoTo Failed
    CPPreflight
    Set fso = CreateObject("Scripting.FileSystemObject")
    Set stream = fso.OpenTextFile(filename, 1, False, -1)
    header = Split(stream.ReadLine, vbTab)
    CPRequire UBound(header) = 1, "Invalid prior journal."
    CPRequire header(0) = "CPJ1", "Invalid prior journal version."
    runID = header(1)
    CPRequire stream.ReadLine = CPFileName, "Prior journal belongs to another DGN path."
    CPRequire stream.ReadLine = CPModelName, "Prior journal belongs to another model."
    CPRequire stream.ReadLine = CPNumber(CDbl(ActiveDesignFile.DateCreated)), "Prior journal belongs to a different DGN file."
    Do While Not stream.AtEndOfStream
        line = stream.ReadLine
        row = Split(line, vbTab)
        If row(0) = "ID" Then
            CPRequire UBound(row) = 2, "Invalid journal ID record."
            ids.Add CStr(row(1))
            stamps.Add CStr(row(2))
        Else
            lastLine = line
            CPRequire stream.AtEndOfStream, "Trailing or unknown journal records."
        End If
    Loop
    stream.Close
    CPRequire lastLine = "COMMITTED" & vbTab & CStr(ids.Count), "Prior insertion was not committed; follow recovery instructions."
    ' Resolve and check every recorded ID/tag before the first removal.
    For i = 1 To ids.Count
        Set element = CPFindElement(CStr(ids(i)))
        If element Is Nothing Then
            missing = missing + 1
        Else
            CPRequire CPTagValue(element) = "CP1|" & runID, "Prior ID/tag mismatch; no previous elements were deleted."
            CPRequire Not element.IsLocked And element.level.ElementAccess = msdLevelElementAccessAll, "Prior element is locked; replacement retained."
            If CPNumber(CDbl(element.DateLastModified)) <> CStr(stamps(i)) Then changed = changed + 1
        End If
    Next i
    message = "The replacement is complete. Remove " & CStr(ids.Count - missing) & " recorded elements from prior run " & runID & "?" & vbCrLf & _
        CStr(changed) & " element timestamps changed; " & CStr(missing) & " elements are already absent." & vbCrLf & _
        "This includes any manually edited members of that run. Copies with new element IDs are preserved." & vbCrLf & _
        "Choose No to keep both runs for review."
    If MsgBox(message, vbYesNo + vbExclamation + vbDefaultButton2, "Confirm staged replacement") <> vbYes Then Exit Sub
    CPPreflight
    For i = 1 To ids.Count
        Set element = CPFindElement(CStr(ids(i)))
        If Not element Is Nothing Then
            CPRequire CPTagValue(element) = "CP1|" & runID, "Prior ID/tag changed; removal stopped."
            CPModel.RemoveElement element
            removed = removed + 1
        End If
        If i Mod 128 = 0 Then
            CPStatus "Removing recorded prior output: " & CStr(i) & "/" & CStr(ids.Count)
            CPPreflight
        End If
    Next i
    MsgBox "Removed " & CStr(removed) & " recorded prior elements. Replacement retained.", vbInformation, "Contour Plotter"
    Exit Sub
Failed:
    message = Err.Description
    On Error Resume Next
    If Not stream Is Nothing Then stream.Close
    On Error GoTo 0
    Err.Raise vbObjectError + 2814, "Contour Plotter", message & vbCrLf & _
        "Replacement retained. Prior elements removed: " & CStr(removed) & ". Keep both run folders for recovery."
End Sub

Public Function CPFindElement(ByVal value As String) As element
    Dim id As DLong
    id = DLongFromString(value)
    ' GetElementByID returns Nothing for an absent ID; unexpected COM errors propagate.
    Set CPFindElement = CPModel.GetElementByID(id)
End Function

Public Sub ListTaggedRuns()
    Dim ee As ElementEnumerator, element As element, counts As Object, tag As String, key As Variant, message As String
    On Error GoTo Failed
    Set counts = CreateObject("Scripting.Dictionary")
    Set ee = ActiveModelReference.Scan
    Do While ee.MoveNext
        Set element = ee.Current
        tag = CPTagValue(element)
        If Len(tag) > 0 Then
            If Not counts.Exists(tag) Then counts.Add tag, 0
            counts(tag) = counts(tag) + 1
        End If
    Loop
    For Each key In counts.keys
        message = message & CStr(key) & ": " & CStr(counts(key)) & vbCrLf
    Next key
    If Len(message) = 0 Then message = "No Contour Plotter tags found in the active model."
    MsgBox message, vbInformation, "Contour Plotter run inventory (read only)"
    Exit Sub
Failed:
    MsgBox Err.Description, vbExclamation, "Contour Plotter"
End Sub

Attribute VB_Name = "modContourImport"
Option Explicit
' SPDX-License-Identifier: MIT
Private mBounds(0 To 3) As Double, mDimension As Long, mExpectedZ As Double

Public Function CPParseNumber(ByVal text As String) As Double
    Static re As Object
    If re Is Nothing Then
        Set re = CreateObject("VBScript.RegExp")
        re.Pattern = "^-?[0-9]+(\.[0-9]+)?([eE][+-]?[0-9]+)?$"
    End If
    CPRequire Len(text) <= 64 And re.Test(text), "Invalid invariant number in engine output: " & Left$(text, 64)
    CPParseNumber = Val(text)
    CPRequire Abs(CPParseNumber) <= 1000000000000#, "Engine number exceeds the coordinate safety range."
End Function

Private Function CPInteger(ByVal text As String, ByVal minimum As Long, ByVal maximum As Long) As Long
    Dim value As Double
    value = CPParseNumber(text)
    CPRequire value = Fix(value) And value >= minimum And value <= maximum, "Invalid integer/count in engine output."
    CPInteger = CLng(value)
End Function

Private Function CPFields(ByVal f As Integer) As Variant
    Dim line As String
    CPRequire Not EOF(f), "Truncated contour output."
    Line Input #f, line
    CPRequire Len(line) > 0 And Len(line) <= 4096, "Invalid contour record length."
    CPFields = Split(line, vbTab)
End Function

Private Function CPPoint(ByVal x As String, ByVal y As String, ByVal z As String) As Point3d
    Dim p As Point3d, tolerance As Double
    p.x = CPParseNumber(x): p.y = CPParseNumber(y): p.z = CPParseNumber(z)
    tolerance = 2# / CPUOR + (Abs(p.x) + Abs(p.y)) * 0.00000000000001
    CPRequire p.x >= mBounds(0) - tolerance And p.x <= mBounds(2) + tolerance, "X outside confirmed source bounds."
    CPRequire p.y >= mBounds(1) - tolerance And p.y <= mBounds(3) + tolerance, "Y outside confirmed source bounds."
    CPRequire Abs(p.z - mExpectedZ) <= 2# / CPUOR + Abs(mExpectedZ) * 0.00000000000001, "Z differs from contour elevation."
    If mDimension = 2 Then CPRequire p.z = 0#, "Nonzero elevation in 2D output."
    CPPoint = p
End Function

Public Function CPImport(ByVal filename As String, ByVal job As String, ByVal runID As String, _
        ByVal majorLevel As String, ByVal minorLevel As String, ByVal majorLabel As String, ByVal minorLabel As String, _
        ByVal styleName As String, ByVal height As Double, ByVal minorHeight As Double, _
        ByVal boxHeight As Double, ByVal minorBoxHeight As Double, ByVal useByLevel As Boolean, _
        ByVal overrideColor As Long, ByVal overrideWeight As Long, ByVal overrideStyle As String, _
        ByVal sourceContext As String, ByVal expectedDimension As Long) As String
    Dim f As Integer, pass As Long, header As Variant, row As Variant, vertex As Variant
    Dim expected(0 To 2) As Long, counts(0 To 2) As Long, i As Long, n As Long, kind As String
    Dim p As Point3d, points() As Point3d, element As element, text As TextElement
    Dim levels(0 To 3) As level, target As level, added As New Collection, journal As Object, fso As Object
    Dim w As Double, h As Double, angle As Double, reservedWidth As Double, labelHeight As Double
    Dim expectedHeight As Double, expectedBoxHeight As Double
    Dim reason As String, remaining As Long, journalName As String, started As Double, checked As Double
    Dim explicitStyle As LineStyle
    On Error GoTo Failed
    CPPreflight
    If Not useByLevel Then
        CPRequire overrideColor >= 0 And overrideColor <= 255 And overrideWeight >= 0 And overrideWeight <= 31, "Invalid symbology override."
        CPRequire Len(overrideStyle) > 0, "Enter an existing line style override."
        Set explicitStyle = ActiveDesignFile.LineStyles.item(overrideStyle)
        CPRequire Not explicitStyle Is Nothing, "Line style override unavailable."
    End If
    Set levels(0) = CPLevel(majorLevel): Set levels(1) = CPLevel(minorLevel)
    If Len(majorLabel) > 0 Then Set levels(2) = CPLevel(majorLabel)
    If Len(minorLabel) > 0 Then Set levels(3) = CPLevel(minorLabel)
    f = FreeFile
    ' Hold a deny-write lock through BOTH passes so validation applies to inserted bytes.
    Open filename For Input Access Read Lock Write As #f
    started = Timer
    For pass = 1 To 2
        Seek #f, 1
        header = CPFields(f)
        CPRequire UBound(header) = 13, "Invalid CP2 header."
        CPRequire header(0) = "CP2" And header(1) = runID, "Unexpected contour output version/run."
        CPRequire header(2) = CPUnitName, "Output/model unit mismatch."
        CPRequire header(3) = "m" Or header(3) = "ft" Or header(3) = "us-ft", "Unresolved output vertical unit."
        For i = 0 To 2
            expected(i) = CPInteger(CStr(header(i + 4)), 0, 100000000)
            counts(i) = 0
        Next i
        CPRequire CPParseNumber(CStr(header(7))) = height, "Output text height changed."
        CPRequire CPParseNumber(CStr(header(8))) = minorHeight, "Minor output text height changed."
        For i = 0 To 3
            mBounds(i) = CPParseNumber(CStr(header(i + 9)))
        Next i
        CPRequire mBounds(2) >= mBounds(0) And mBounds(3) >= mBounds(1), "Invalid source bounds."
        mDimension = CPInteger(CStr(header(13)), 2, 3)
        CPRequire mDimension = expectedDimension, "Output dimension differs from the requested setting."
        If mDimension = 3 Then CPRequire CPModel.Is3D, "3D contours require a 3D design model."
        If pass = 2 Then
            CPPreflight
            CPRequire MsgBox("Insert into:" & vbCrLf & CPFileName & vbCrLf & CPModelName & _
                vbCrLf & CStr(expected(0)) & " line strings; " & CStr(expected(1)) & " ordinary text elements." & _
                vbCrLf & "Model units: " & CPUnitName & "; elevation labels: " & CStr(header(3)) & _
                vbCrLf & "Bounds: " & CStr(header(9)) & ", " & CStr(header(10)) & " to " & CStr(header(11)) & ", " & CStr(header(12)) & _
                vbCrLf & "Contour levels: " & majorLevel & " / " & minorLevel & vbCrLf & sourceContext & _
                vbCrLf & CPGcsName & vbCrLf & "Confirm this source grid, axis mapping, vertical datum and location match the active model.", _
                vbYesNo + vbExclamation + vbDefaultButton2, "Confirm native DGN placement") = vbYes, "Placement cancelled before insertion."
            journalName = job & "\elements.cpj"
            CPStartJournal journalName, runID, journal
        End If
        Do
            row = CPFields(f)
            kind = CStr(row(0))
            If kind = "E" Then
                CPRequire UBound(row) = 3, "Invalid CP2 footer."
                For i = 0 To 2
                    CPRequire CPInteger(CStr(row(i + 1)), 0, 100000000) = counts(i), "Footer count mismatch."
                    CPRequire counts(i) = expected(i), "Header count mismatch."
                Next i
                CPRequire EOF(f), "Unexpected data after CP2 footer."
                Exit Do
            End If
            CPRequire kind = "C" Or kind = "L", "Unknown contour record."
            If kind = "C" Then
                CPRequire UBound(row) = 4, "Invalid contour record."
            Else
                CPRequire UBound(row) = 10, "Invalid label record."
            End If
            Call CPInteger(CStr(row(1)), 1, 100000000)
            mExpectedZ = 0#
            If mDimension = 3 Then mExpectedZ = CPParseNumber(CStr(row(2))) * CPMetres(CStr(header(3))) / CPMetres(CPUnitName)
            Call CPParseNumber(CStr(row(2)))
            CPRequire row(3) = "M" Or row(3) = "m", "Invalid contour classification."
            If kind = "C" Then
                n = CPInteger(CStr(row(4)), 2, 1024)
                ReDim points(0 To n - 1)
                For i = 0 To n - 1
                    vertex = CPFields(f)
                    CPRequire UBound(vertex) = 3, "Invalid vertex record."
                    CPRequire vertex(0) = "V", "Expected a vertex."
                    points(i) = CPPoint(CStr(vertex(1)), CStr(vertex(2)), CStr(vertex(3)))
                    If i > 0 Then
                        CPRequire points(i).x <> points(i - 1).x Or points(i).y <> points(i - 1).y, "Duplicate consecutive contour vertex."
                    End If
                Next i
                Set element = CreateLineElement1(Nothing, points)
                If row(3) = "M" Then Set target = levels(0) Else Set target = levels(1)
                counts(0) = counts(0) + 1: counts(2) = counts(2) + n
            Else
                p = CPPoint(CStr(row(4)), CStr(row(5)), CStr(row(6)))
                angle = CPParseNumber(CStr(row(7)))
                labelHeight = CPParseNumber(CStr(row(8)))
                reservedWidth = CPParseNumber(CStr(row(9)))
                If row(3) = "M" Then
                    expectedHeight = height: expectedBoxHeight = boxHeight
                Else
                    expectedHeight = minorHeight: expectedBoxHeight = minorBoxHeight
                End If
                CPRequire Abs(angle) <= 1.570796326795 And labelHeight = expectedHeight And reservedWidth > 0, "Invalid text angle/footprint."
                CPRequire CPParseNumber(CStr(row(10))) = CPParseNumber(CStr(row(2))), "Label value differs from elevation."
                Set text = CPText(CStr(row(10)), p, angle, labelHeight, styleName)
                text.GetTotalTextSize w, h
                CPRequire w <= reservedWidth + 2# / CPUOR And h <= expectedBoxHeight + 2# / CPUOR, "Font footprint changed; analyze and measure again."
                Set element = text
                If row(3) = "M" Then Set target = levels(2) Else Set target = levels(3)
                CPRequire Not target Is Nothing, "Required label level missing."
                counts(1) = counts(1) + 1
            End If
            If pass = 2 Then
                CPTag element, runID
                added.Add element
                CPModel.AddElement element
                CPApply element, target, useByLevel, overrideColor, overrideWeight, overrideStyle
                CPRequire CPTagValue(element) = "CP1|" & runID, "Persistent run tag did not survive Rewrite."
                journal.WriteLine "ID" & vbTab & DLongToString(element.id) & vbTab & CPNumber(CDbl(element.DateLastModified))
                If added.Count Mod 128 = 0 Then
                    journal.Close
                    Set journal = CreateObject("Scripting.FileSystemObject").OpenTextFile(journalName, 8, False, -1)
                End If
            End If
            If (counts(0) + counts(1)) Mod 128 = 0 Then
                CPStatus "Pass " & CStr(pass) & "/2: " & CStr(counts(0) + counts(1)) & " elements"
                CPPreflight
            End If
        Loop
        If pass = 1 Then checked = Timer
    Next pass
    CPPreflight
    Close #f: f = 0
    journal.WriteLine "COMMITTED" & vbTab & CStr(added.Count)
    journal.Close
    Set journal = Nothing
    CPImport = "Inserted " & CStr(counts(0)) & " line strings and " & CStr(counts(1)) & " text elements." & vbCrLf & _
        "Validation: " & Format$(CPElapsed(started, checked), "0.00") & " s; insertion: " & _
        Format$(CPElapsed(checked, Timer), "0.00") & " s." & vbCrLf & "Run folder: " & job
    Exit Function
Failed:
    reason = Err.Description
    On Error Resume Next
    If f <> 0 Then Close #f
    If Not journal Is Nothing Then journal.Close
    remaining = CPRollback(added, runID)
    On Error GoTo 0
    Err.Raise vbObjectError + 2815, "Contour Plotter", reason & vbCrLf & _
        "New elements still requiring inspection: " & CStr(remaining) & ". Previous successful output was retained." & vbCrLf & _
        "Recovery folder: " & job
End Function

Private Function CPElapsed(ByVal first As Double, ByVal last As Double) As Double
    CPElapsed = last - first
    If CPElapsed < 0# Then CPElapsed = CPElapsed + 86400#
End Function

Private Function CPMetres(ByVal unit As String) As Double
    Select Case unit
        Case "m": CPMetres = 1#
        Case "ft": CPMetres = 0.3048
        Case "us-ft": CPMetres = 1200# / 3937#
        Case Else: CPRequire False, "Unsupported CP2 linear unit."
    End Select
End Function

Attribute VB_Name = "modContourLabels"
Option Explicit
' SPDX-License-Identifier: MIT
Public Function CPText(ByVal value As String, origin As Point3d, ByVal angle As Double, _
        ByVal height As Double, ByVal styleName As String) As TextElement
    Dim text As TextElement, style As TextStyle, rotation As Matrix3d, ratio As Double
    Dim actualWidth As Double, actualHeight As Double
    Set style = CPStyle(styleName)
    ratio = style.width / style.height
    rotation = Matrix3dFromAxisAndRotationAngle(2, angle)
    Set text = CreateTextElement1(Nothing, value, origin, rotation)
    Set text.TextStyle = style
    ' Change the element's local style; never change the object fetched from the DGN table.
    text.TextStyle.height = height
    text.TextStyle.width = height * ratio
    text.TextStyle.Justification = msdTextJustificationCenterCenter
    text.TextStyle.UsesColor = False
    text.TextStyle.BorderAndBackgroundVisible = False
    Set style = text.TextStyle
    Set text.TextStyle = style
    text.GetTotalTextSize actualWidth, actualHeight
    CPRequire actualWidth > 0# And actualHeight > 0#, "Text style produced an invalid physical footprint."
    ' Normalize model-space geometry without changing active annotation scale.
    text.ScaleUniform origin, height / actualHeight
    text.origin = origin
    text.GetTotalTextSize actualWidth, actualHeight
    CPRequire Abs(actualHeight - height) <= 2# / CPUOR, "Text physical height could not be calibrated."
    Set CPText = text
End Function

Public Function CPMeasuredWidths(ByVal job As String, ByVal styleName As String, _
        ByVal height As Double, ByVal minorHeight As Double, ByRef boxHeight As Double, ByRef minorBoxHeight As Double) As String
    Dim f As Integer, line As String, text As TextElement, p As Point3d
    Dim w As Double, h As Double, result As String, message As String, fields As Variant, textHeight As Double
    On Error GoTo Failed
    boxHeight = height: minorBoxHeight = minorHeight
    result = "{"
    f = FreeFile
    Open job & "\levels.tsv" For Input Access Read Lock Write As #f
    Do While Not EOF(f)
        Line Input #f, line
        fields = Split(line, vbTab)
        CPRequire UBound(fields) = 1, "Invalid classified elevation from engine."
        line = CStr(fields(0))
        CPRequire Len(line) > 0 And Len(line) <= 64, "Invalid elevation text from engine."
        CPRequire fields(1) = "M" Or fields(1) = "m", "Invalid elevation class."
        Call CPParseNumber(line)
        If fields(1) = "M" Then textHeight = height Else textHeight = minorHeight
        Set text = CPText(line, p, 0#, textHeight, styleName)
        text.GetTotalTextSize w, h
        CPRequire w > 0 And h > 0, "The DGN font could not be measured."
        If Len(result) > 1 Then result = result & ","
        result = result & CPJson(line) & ":" & CPNumber(w)
        If fields(1) = "M" Then
            If h > boxHeight Then boxHeight = h
        Else
            If h > minorBoxHeight Then minorBoxHeight = h
        End If
    Loop
    Close #f
    CPMeasuredWidths = result & "}"
    Exit Function
Failed:
    message = Err.Description
    On Error Resume Next
    If f <> 0 Then Close #f
    On Error GoTo 0
    Err.Raise vbObjectError + 2811, "Contour Plotter", message
End Function

Attribute VB_Name = "modLevelManager"
Option Explicit
' SPDX-License-Identifier: MIT
Public Sub CPFillLevels(ByVal box As MSForms.ComboBox, ByVal preference As String)
    Dim item As level, previous As String, i As Long
    previous = GetSetting(CP_APP, "Levels", preference, "")
    box.Clear
    For Each item In ActiveDesignFile.levels
        box.AddItem item.name
    Next item
    For i = 0 To box.ListCount - 1
        If StrComp(box.List(i), previous, vbBinaryCompare) = 0 Then box.ListIndex = i
    Next i
End Sub

Public Function CPLevel(ByVal name As String) As level
    Dim selected As level
    CPRequire Len(name) > 0, "Select all required contour/label levels."
    Set selected = ActiveDesignFile.levels.Find(name, Nothing)
    CPRequire Not selected Is Nothing, "Level unavailable in DGN or attached libraries: " & name
    CPRequire StrComp(selected.name, name, vbBinaryCompare) = 0, "Level name must match exactly: " & name
    CPRequire Not selected.IsLocked And selected.ElementAccess = msdLevelElementAccessAll, "Level is not fully writable: " & name
    Set CPLevel = selected
End Function

Public Sub CPFillStyles(ByVal box As MSForms.ComboBox)
    Dim style As TextStyle, previous As String, i As Long
    previous = GetSetting(CP_APP, "Settings", "TextStyle", "")
    box.Clear
    For Each style In ActiveDesignFile.TextStyles
        If Len(style.name) > 0 Then box.AddItem style.name
    Next style
    For i = 0 To box.ListCount - 1
        If StrComp(box.List(i), previous, vbBinaryCompare) = 0 Then box.ListIndex = i
    Next i
End Sub

Public Function CPStyle(ByVal name As String) As TextStyle
    Dim style As TextStyle
    CPRequire Len(name) > 0, "Select an existing DGN/library text style."
    Set style = ActiveDesignFile.TextStyles.Find(name, Nothing)
    CPRequire Not style Is Nothing, "Text style unavailable: " & name
    CPRequire StrComp(style.name, name, vbBinaryCompare) = 0, "Text style name must match exactly: " & name
    CPRequire style.height > 0 And style.width > 0, "Text style needs positive height and width."
    ' Cache the selected existing definition so element-local overrides are editable.
    If style.IsFromLibrary Then Set style = ActiveDesignFile.TextStyles.Add(style, name)
    Set CPStyle = style
End Function

Attribute VB_Name = "modPythonBridge"
Option Explicit
' SPDX-License-Identifier: MIT
Private Type CPGuid
    Data1 As Long
    Data2 As Integer
    Data3 As Integer
    Data4(0 To 7) As Byte
End Type
Private Declare PtrSafe Function CoCreateGuid Lib "ole32.dll" (ByRef value As CPGuid) As Long
Private Type CPOpenFileName
    size As Long
    owner As LongPtr
    instance As LongPtr
    filter As LongPtr
    customFilter As LongPtr
    maxCustomFilter As Long
    filterIndex As Long
    filename As LongPtr
    maxFile As Long
    fileTitle As LongPtr
    maxFileTitle As Long
    initialDirectory As LongPtr
    title As LongPtr
    flags As Long
    fileOffset As Integer
    extensionOffset As Integer
    defaultExtension As LongPtr
    customData As LongPtr
    hook As LongPtr
    templateName As LongPtr
    reserved As LongPtr
    reservedWord As Long
    extraFlags As Long
End Type
Private Type CPStartupInfo
    size As Long
    reserved As LongPtr
    desktop As LongPtr
    title As LongPtr
    x As Long
    y As Long
    width As Long
    height As Long
    xChars As Long
    yChars As Long
    fill As Long
    flags As Long
    showWindow As Integer
    reservedSize As Integer
    reservedBytes As LongPtr
    inputHandle As LongPtr
    outputHandle As LongPtr
    errorHandle As LongPtr
End Type
Private Type CPProcessInfo
    processHandle As LongPtr
    threadHandle As LongPtr
    processID As Long
    threadID As Long
End Type
Private Declare PtrSafe Function CPGetOpenFileName Lib "comdlg32.dll" Alias "GetOpenFileNameW" (ByRef dialog As CPOpenFileName) As Long
Private Declare PtrSafe Function CPDialogError Lib "comdlg32.dll" Alias "CommDlgExtendedError" () As Long
Private Declare PtrSafe Function CPActiveWindow Lib "user32.dll" Alias "GetActiveWindow" () As LongPtr
Private Declare PtrSafe Function CPCreateProcess Lib "kernel32.dll" Alias "CreateProcessW" ( _
    ByVal applicationName As LongPtr, ByVal commandLine As LongPtr, ByVal processSecurity As LongPtr, _
    ByVal threadSecurity As LongPtr, ByVal inheritHandles As Long, ByVal flags As Long, _
    ByVal environment As LongPtr, ByVal directory As LongPtr, ByRef startup As CPStartupInfo, _
    ByRef process As CPProcessInfo) As Long
Private Declare PtrSafe Function CPWaitForProcess Lib "kernel32.dll" Alias "WaitForSingleObject" (ByVal handle As LongPtr, ByVal milliseconds As Long) As Long
Private Declare PtrSafe Function CPExitCode Lib "kernel32.dll" Alias "GetExitCodeProcess" (ByVal handle As LongPtr, ByRef code As Long) As Long
Private Declare PtrSafe Function CPCloseHandle Lib "kernel32.dll" Alias "CloseHandle" (ByVal handle As LongPtr) As Long

Public Function CPNewRunID() As String
    Dim value As CPGuid, i As Long, tail As String
    CPRequire CoCreateGuid(value) = 0, "Windows could not create a unique run ID."
    For i = 0 To 7
        tail = tail & Right$("00" & Hex$(value.Data4(i)), 2)
    Next i
    CPNewRunID = LCase$(Right$("00000000" & Hex$(value.Data1), 8) & "-" & _
        Right$("0000" & Hex$(value.Data2), 4) & "-" & Right$("0000" & Hex$(value.Data3), 4) & "-" & _
        Left$(tail, 4) & "-" & Mid$(tail, 5))
End Function

Public Function CPNewJob(ByVal runID As String) As String
    Dim fso As Object, root As String
    Set fso = CreateObject("Scripting.FileSystemObject")
    root = Environ$("LOCALAPPDATA") & "\ContourPlotter"
    If Not fso.FolderExists(root) Then fso.CreateFolder root
    root = root & "\jobs"
    If Not fso.FolderExists(root) Then fso.CreateFolder root
    CPNewJob = root & "\" & runID
    CPRequire Not fso.FolderExists(CPNewJob), "Run folder already exists."
    fso.CreateFolder CPNewJob
End Function

Private Function CPQuote(ByVal value As String) As String
    CPRequire InStr(value, Chr$(34)) = 0 And InStr(value, vbCr) = 0 And InStr(value, vbLf) = 0, "Invalid executable or request path."
    CPQuote = Chr$(34) & value & Chr$(34)
End Function

Public Sub CPWriteUTF8(ByVal filename As String, ByVal value As String)
    Dim stream As Object
    Set stream = CreateObject("ADODB.Stream")
    stream.Type = 2
    stream.Charset = "utf-8"
    stream.Open
    stream.WriteText value
    stream.SaveToFile filename, 2
    stream.Close
End Sub

Public Sub CPRunEngine(ByVal executable As String, ByVal job As String, ByVal request As String)
    Dim process As CPProcessInfo, startup As CPStartupInfo, fso As Object, message As String, f As Object
    Dim stopRequested As Boolean, commandLine As String, waitResult As Long, exitCode As Long
    On Error GoTo Failed
    executable = CPPath(executable)
    Set fso = CreateObject("Scripting.FileSystemObject")
    CPRequire fso.FileExists(executable) And LCase$(fso.GetExtensionName(executable)) = "exe", "Browse to the packaged ContourPlotter.exe."
    CPWriteUTF8 job & "\request.json", request
    startup.size = LenB(startup)
    CPRequire startup.size = 104 And LenB(process) = 24, "Unsupported Windows process structure layout."
    startup.flags = 1 ' STARTF_USESHOWWINDOW; showWindow defaults to SW_HIDE.
    commandLine = CPQuote(executable) & " --request " & CPQuote(job & "\request.json")
    ' CREATE_NO_WINDOW prevents a console from being created, even briefly.
    If CPCreateProcess(StrPtr(executable), StrPtr(commandLine), 0, 0, 0, &H8000000, 0, 0, startup, process) = 0 Then
        Err.Raise vbObjectError + 2812, "Contour engine", "Cannot start contour engine (Windows error " & CStr(Err.LastDllError) & ")."
    End If
    CPCloseHandle process.threadHandle: process.threadHandle = 0
    Do
        waitResult = CPWaitForProcess(process.processHandle, 75)
        If waitResult = 0 Then Exit Do
        CPRequire waitResult = 258, "Cannot monitor contour engine."
        DoEvents
        If CPCancelled And Not stopRequested Then
            Set f = fso.CreateTextFile(job & "\cancel", True)
            f.Close
            stopRequested = True
            CPStatus "Cancellation requested; waiting for the current library operation..."
        End If
    Loop
    CPRequire CPExitCode(process.processHandle, exitCode) <> 0, "Cannot read contour engine exit status."
    CPCloseHandle process.processHandle: process.processHandle = 0
    CPRequire Not CPCancelled, "Cancelled. No DGN elements have been inserted."
    If exitCode <> 0 Then
        If fso.FileExists(job & "\error.txt") Then message = CPReadUnicode(job & "\error.txt")
        If Len(message) = 0 Then message = "Contour engine exited with code " & CStr(exitCode) & ". See error.json in " & job
        Err.Raise vbObjectError + 2812, "Contour engine", message
    End If
    CPRequire fso.FileExists(job & "\result.json"), "Engine exited without a successful result."
    Exit Sub
Failed:
    message = Err.Description
    If process.threadHandle <> 0 Then CPCloseHandle process.threadHandle
    If process.processHandle <> 0 Then CPCloseHandle process.processHandle
    Err.Raise vbObjectError + 2812, "Contour engine", message
End Sub

Public Function CPRequest(ByVal action As String, ByVal runID As String, ByVal job As String, _
        ByVal source As String, ByVal Spatial As String, ByVal Settings As String) As String
    CPRequest = "{""version"":1,""action"":" & CPJson(action) & ",""run_id"":" & CPJson(runID) & _
        ",""input"":" & CPJson(CPPath(source)) & ",""output_dir"":" & CPJson(job) & _
        ",""spatial"":" & Spatial & ",""settings"":" & Settings & "}"
End Function

Public Function CPPath(ByVal value As String) As String
    value = Trim$(value)
    If Len(value) >= 2 And Left$(value, 1) = Chr$(34) And Right$(value, 1) = Chr$(34) Then
        value = Mid$(value, 2, Len(value) - 2)
    End If
    CPRequire InStr(value, Chr$(34)) = 0 And InStr(value, vbCr) = 0 And InStr(value, vbLf) = 0 And _
        InStr(value, vbNullChar) = 0 And InStr(value, vbTab) = 0, "Invalid file path: remove unmatched quotes or control characters."
    CPPath = value
End Function

Public Function CPBrowse(ByVal prompt As String, ByVal existing As String, _
        Optional ByVal fileFilter As String = "All files (*.*)|*.*") As String
    Dim dialog As CPOpenFileName, buffer As String, filter As String, folder As String
    Dim fso As Object, errorCode As Long
    On Error GoTo Failed
    existing = CPPath(existing)
    Set fso = CreateObject("Scripting.FileSystemObject")
    If fso.FolderExists(existing) Then
        folder = existing: existing = ""
    Else
        folder = fso.GetParentFolderName(existing)
        If Not fso.FolderExists(folder) Then folder = ""
        If Not fso.FileExists(existing) Then existing = ""
    End If
    CPRequire Len(existing) < 32768, "The existing file path exceeds the picker buffer."
    buffer = existing & String$(32768 - Len(existing), vbNullChar)
    filter = Replace(fileFilter, "|", vbNullChar) & vbNullChar & vbNullChar
    dialog.size = LenB(dialog)
    CPRequire dialog.size = 152, "Unsupported Windows file-picker structure layout."
    dialog.owner = CPActiveWindow()
    dialog.filter = StrPtr(filter): dialog.filterIndex = 1
    dialog.filename = StrPtr(buffer): dialog.maxFile = Len(buffer)
    dialog.title = StrPtr(prompt): dialog.initialDirectory = StrPtr(folder)
    dialog.flags = &H80000 Or &H1000 Or &H800 Or &H8 Or &H4
    If CPGetOpenFileName(dialog) <> 0 Then
        CPBrowse = CPPath(Left$(buffer, InStr(buffer, vbNullChar) - 1))
    Else
        errorCode = CPDialogError()
        CPRequire errorCode = 0, "Windows file picker failed (error 0x" & Hex$(errorCode) & ")."
    End If
    Exit Function
Failed:
    MsgBox Err.Description, vbExclamation, "Contour Plotter"
End Function
