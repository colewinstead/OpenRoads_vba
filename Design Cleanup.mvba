Attribute VB_Name = "ModDesign_Cleanup"
Option Explicit

Private Const GRID_TRANSPARENCY As Double = 0.4
Private Const NORMAL_TRANSPARENCY As Double = 0#

'=============================================================
' MAIN COMMAND
'=============================================================
Public Sub Batch_All_XS_Drawing_Models()

    Dim modelCount As Long
    Dim originalModelName As String

    Dim errorNumber As Long
    Dim errorDescription As String
    Dim errorSource As String

    On Error GoTo BatchError

    originalModelName = ActiveModelReference.Name
    modelCount = 0

    ProcessActiveXSDrawingModels modelCount

    'Return to the model that was active before the batch.
    ActiveDesignFile.Models.Item(originalModelName).Activate

    TurnAllLevelsOn

    CadInputQueue.SendCommand "FILEDESIGN SAVESETTINGS"
    CadInputQueue.SendCommand "FILEDESIGN"
    DoEvents

    MsgBox CStr(modelCount) & _
           " cross-section drawing model(s) processed.", _
           vbInformation, _
           "XS Cleanup Complete"

    Exit Sub

BatchError:

    'Capture the error before running any recovery commands.
    errorNumber = Err.Number
    errorDescription = Err.Description
    errorSource = Err.Source

    On Error Resume Next

    TurnAllLevelsOn
    CommandState.StartDefaultCommand

    MsgBox "The batch process stopped." & _
           vbCrLf & vbCrLf & _
           "Error number: " & CStr(errorNumber) & _
           vbCrLf & _
           "Source: " & errorSource & _
           vbCrLf & _
           "Description: " & errorDescription & _
           vbCrLf & vbCrLf & _
           "Models completed: " & CStr(modelCount), _
           vbExclamation, _
           "XS Cleanup Error"

End Sub


'=============================================================
' COLLECTS AND PROCESSES ALL XS DRAWING MODELS
'=============================================================
Private Sub ProcessActiveXSDrawingModels( _
    ByRef modelCount As Long)

    Dim modelNames As Collection
    Dim oModel As ModelReference
    Dim modelName As Variant

    Set modelNames = New Collection

    'Collect names before changing the active model.
    For Each oModel In ActiveDesignFile.Models

        If IsXsDrawingModel(oModel) Then
            modelNames.Add oModel.Name
        End If

    Next oModel

    'Process each XS drawing model.
    For Each modelName In modelNames

        Set oModel = _
            ActiveDesignFile.Models.Item(CStr(modelName))

        oModel.Activate
        DoEvents

        'All levels visible before cleanup.
        TurnAllLevelsOn

        'Run the recorded cleanup command.
        BmrDesign_Cleanup

        'Correct transparency using one model scan.
        SetTransparencyByLevel oModel

        'Leave all levels visible.
        TurnAllLevelsOn

        modelCount = modelCount + 1

    Next modelName

End Sub


'=============================================================
' IDENTIFIES XS DRAWING MODELS
'
' Processes:
'   78.4 - 277+50.0000
'
' Skips:
'   78.4 - 277+50.0000 [Sheet]
'=============================================================
Private Function IsXsDrawingModel( _
    ByVal oModel As ModelReference) As Boolean

    Dim modelName As String

    IsXsDrawingModel = False

    modelName = UCase$(Trim$(oModel.Name))

    'Only process drawing models.
    If oModel.Type <> msdModelTypeDrawing Then Exit Function

    'XS model names contain station notation.
    If InStr(1, modelName, "+", vbTextCompare) = 0 Then Exit Function

    'Do not process sheet models.
    If InStr(1, modelName, "[SHEET]", vbTextCompare) > 0 Then Exit Function

    IsXsDrawingModel = True

End Function


'=============================================================
' RECORDED DESIGN FILE CLEANUP COMMAND
'=============================================================
Public Sub BmrDesign_Cleanup()

    Dim startPoint As Point3d
    Dim point As Point3d

    On Error GoTo CleanupError

    TurnAllLevelsOn
    DoEvents

    CadInputQueue.SendCommand "MDL SILENTLOAD CLEANUP"
    DoEvents

    CadInputQueue.SendCommand "CLEANUP DO"
    DoEvents

    CadInputQueue.SendCommand "DMSG UPDATEDIALOG -400"
    DoEvents

    'Coordinates are in master units.
    startPoint.X = -29.0580010203581
    startPoint.Y = 253.791768003982
    startPoint.Z = 0#

    point.X = startPoint.X
    point.Y = startPoint.Y
    point.Z = startPoint.Z

    CadInputQueue.SendDataPoint point, 1
    DoEvents

    CommandState.StartDefaultCommand
    DoEvents

    Exit Sub

CleanupError:

    Dim errorNumber As Long
    Dim errorDescription As String

    errorNumber = Err.Number
    errorDescription = Err.Description

    On Error Resume Next
    CommandState.StartDefaultCommand
    On Error GoTo 0

    Err.Raise errorNumber, _
              "BmrDesign_Cleanup", _
              errorDescription

End Sub


'=============================================================
' SCANS THE MODEL ONCE AND CORRECTS TRANSPARENCY
'
' Grid levels:
'   Transparency = 0.4, or 40%
'
' Every other level:
'   Transparency = 0
'
' Elements already having the correct value are not rewritten.
'=============================================================
Private Sub SetTransparencyByLevel( _
    ByVal oModel As ModelReference)

    Dim scanCriteria As ElementScanCriteria
    Dim elementEnumerator As elementEnumerator
    Dim elementsToChange As Collection
    Dim transparencyValues As Collection

    Dim oElement As Element
    Dim oLevel As Level

    Dim levelName As String
    Dim targetTransparency As Double
    Dim currentTransparency As Double

    Dim i As Long
    Dim changedCount As Long

    Dim errorNumber As Long
    Dim errorDescription As String

    On Error GoTo TransparencyError

    Set scanCriteria = New ElementScanCriteria
    Set elementsToChange = New Collection
    Set transparencyValues = New Collection

    Set elementEnumerator = oModel.Scan(scanCriteria)

    If elementEnumerator Is Nothing Then Exit Sub

    'Collect elements that actually require a change.
    Do While elementEnumerator.MoveNext

        Set oElement = Nothing
        Set oLevel = Nothing

        Set oElement = elementEnumerator.Current

        If Not oElement Is Nothing Then

            If ElementCanBeProcessed(oElement) Then

                'Some special elements do not return a valid Level object.
                On Error Resume Next
                Set oLevel = oElement.Level
                On Error GoTo TransparencyError

                If Not oLevel Is Nothing Then

                    levelName = UCase$(Trim$(oLevel.Name))

                    If IsGridLevel(levelName) Then
                        targetTransparency = GRID_TRANSPARENCY
                    Else
                        targetTransparency = NORMAL_TRANSPARENCY
                    End If

                    If TryGetTransparency( _
                            oElement, _
                            currentTransparency) Then

                        If Abs(currentTransparency - _
                               targetTransparency) > 0.001 Then

                            elementsToChange.Add oElement
                            transparencyValues.Add targetTransparency

                        End If

                    End If

                End If

            End If

        End If

    Loop

    'Rewrite only elements with an incorrect transparency value.
    For i = 1 To elementsToChange.Count

        Set oElement = Nothing
        Set oElement = elementsToChange.Item(i)

        If Not oElement Is Nothing Then

            targetTransparency = _
                CDbl(transparencyValues.Item(i))

            If SetOneElementTransparency( _
                    oElement, _
                    targetTransparency) Then

                changedCount = changedCount + 1

            End If

        End If

    Next i

    If changedCount > 0 Then
        RedrawAllViews
    End If

    Exit Sub

TransparencyError:

    errorNumber = Err.Number
    errorDescription = Err.Description

    Err.Raise errorNumber, _
              "SetTransparencyByLevel", _
              errorDescription

End Sub


'=============================================================
' RETURNS TRUE FOR THE THREE GRID LEVELS
'=============================================================
Private Function IsGridLevel( _
    ByVal levelName As String) As Boolean

    Select Case UCase$(Trim$(levelName))

        Case "XS_SHEET_MAJOR_GRIDS", _
             "XS_SHEET_MEDIUM_GRIDS", _
             "XS_SHEET_MINOR_GRIDS"

            IsGridLevel = True

        Case Else

            IsGridLevel = False

    End Select

End Function


'=============================================================
' CHECKS WHETHER THE ELEMENT CAN BE MODIFIED
'=============================================================
Private Function ElementCanBeProcessed( _
    ByVal oElement As Element) As Boolean

    On Error GoTo CannotProcess

    ElementCanBeProcessed = False

    If oElement Is Nothing Then Exit Function
    If Not oElement.IsGraphical Then Exit Function

    Select Case oElement.Type

        Case msdElementTypeReferenceAttachment, _
             msdElementTypeRasterReference, _
             msdElementTypeRasterHeader, _
             msdElementTypeRasterComponent, _
             msdElementTypeSharedCellDefinition

            Exit Function

    End Select

    ElementCanBeProcessed = True
    Exit Function

CannotProcess:

    Err.Clear
    ElementCanBeProcessed = False

End Function


'=============================================================
' SAFELY READS AN ELEMENT'S CURRENT TRANSPARENCY
'=============================================================
Private Function TryGetTransparency( _
    ByVal oElement As Element, _
    ByRef transparencyValue As Double) As Boolean

    On Error GoTo ReadFailed

    transparencyValue = oElement.Transparency
    TryGetTransparency = True

    Exit Function

ReadFailed:

    Err.Clear
    TryGetTransparency = False

End Function


'=============================================================
' SAFELY CHANGES AND REWRITES ONE ELEMENT
'=============================================================
Private Function SetOneElementTransparency( _
    ByVal oElement As Element, _
    ByVal transparencyValue As Double) As Boolean

    On Error GoTo ChangeFailed

    oElement.Transparency = transparencyValue
    oElement.Rewrite

    SetOneElementTransparency = True
    Exit Function

ChangeFailed:

    Err.Clear
    SetOneElementTransparency = False

End Function


'=============================================================
' TURNS ALL LEVELS ON IN VIEW 1
'=============================================================
Private Sub TurnAllLevelsOn()

    CadInputQueue.SendKeyin _
        "SET LEVELS ON ALL;SELVIEW 1"

End Sub
