Attribute VB_Name = "PerpendicularLineGeneratorMain"
Option Explicit

' Key-in: VBA RUN [PerpendicularLineGenerator]PerpendicularLineGeneratorMain.Main
Private mSource As Element
Private mModel As ModelReference
Private mSessionActive As Boolean
Private mStatus As String
Private mPicker As clsPerpendicularLocate

Public Sub Main()
    On Error GoTo Failed
    If mSessionActive Then Exit Sub
    PLGRequire ActiveModelReference.Type <> msdModelTypeSheet, "Open the alignment's design/drawing model before running this tool. Sheet models are excluded."
    CommandState.StartLocate New clsPerpendicularLocate
    Exit Sub
Failed:
    MsgBox Err.Description, vbExclamation, "Perpendicular Line Generator"
    CommandState.StartDefaultCommand
End Sub

Public Function PLGBeginAlignment(source As Element) As Boolean
    Dim reason As String
    On Error GoTo Failed
    If mSessionActive Then Exit Function
    PLGRequire ActiveModelReference.Type <> msdModelTypeSheet, "Open the alignment's design/drawing model before running this tool. Sheet models are excluded."
    PLGRequire source.ModelReference.IsActive And Not source.ModelReference.IsAttachment, _
        "Select geometry in the active model. Reference attachments are not supported."
    If Not PLGLoadPath(source, reason) Then
        MsgBox reason, vbExclamation, "Unsupported alignment"
        Exit Function
    End If
    Set mSource = source
    Set mModel = ActiveModelReference
    mSessionActive = True
    mStatus = reason
    frmPerpendicularLines.RefreshContext mStatus
    BeginRangePick 1, True
    PLGBeginAlignment = True
    Exit Function
Failed:
    MsgBox Err.Description, vbExclamation, "Perpendicular Line Generator"
    PLGCloseSession
End Function

Public Sub PLGCloseSession()
    Set mPicker = Nothing
    mSessionActive = False
    Set mSource = Nothing
    Set mModel = Nothing
    PLGClearPath
End Sub

Public Function PLGPickContextValid() As Boolean
    On Error GoTo Done
    If Not mSessionActive Then Exit Function
    If mModel Is Nothing Then Exit Function
    PLGPickContextValid = mModel.IsActive
Done:
End Function

Private Sub ShowSettingsDialog()
    Dim target As Long
    On Error GoTo Failed
    PLGRequire PLGPickContextValid(), "The active model changed. Run the tool again."
    frmPerpendicularLines.PrepareDialog mStatus
    frmPerpendicularLines.Show vbModal
    target = frmPerpendicularLines.RequestedPick
    If target > 0 Then
        BeginRangePick target, False
    Else
        PLGCloseSession
    End If
    Exit Sub
Failed:
    MsgBox Err.Description, vbExclamation, "Perpendicular Line Generator"
    PLGCloseSession
End Sub

Private Sub BeginRangePick(ByVal target As Long, ByVal followWithEnd As Boolean)
    Dim reverse As Boolean, previewLength As Double, placement As Long, firstDistance As Double
    Dim errorText As String, stopError As Long
    On Error GoTo Failed
    PLGRequire PLGPickContextValid(), "The active model changed. Run the tool again."
    frmPerpendicularLines.ReadPickSettings target, reverse, previewLength, placement, firstDistance
    Set mPicker = New clsPerpendicularLocate
    mPicker.ConfigurePick target, reverse, previewLength, placement, firstDistance, followWithEnd
    CommandState.StartPrimitive mPicker
    Exit Sub
Failed:
    errorText = Err.Description
    On Error Resume Next
    Err.Clear
    If Not mPicker Is Nothing Then mPicker.StopPick Else CommandState.StartDefaultCommand
    stopError = Err.Number
    Set mPicker = Nothing
    On Error GoTo 0
    If stopError <> 0 Then
        PLGCloseSession
        MsgBox errorText & vbCrLf & "The picker could not be stopped. Start another ORD command before retrying.", vbExclamation, "Perpendicular Line Generator"
        Exit Sub
    End If
    MsgBox errorText, vbExclamation, "Perpendicular Line Generator"
    If PLGPickContextValid() Then ShowSettingsDialog Else PLGCloseSession
End Sub

Public Sub PLGFinishRangePick(ByVal target As Long, ByVal accepted As Boolean, _
        ByVal distance As Double, ByVal followWithEnd As Boolean)
    On Error GoTo Failed
    Set mPicker = Nothing
    PLGRequire PLGPickContextValid(), "The active model changed. Run the tool again."
    If accepted Then frmPerpendicularLines.SetPickedDistance target, distance
    If accepted And target = 1 And followWithEnd Then
        BeginRangePick 2, False
    Else
        ShowSettingsDialog
    End If
    Exit Sub
Failed:
    MsgBox Err.Description, vbExclamation, "Perpendicular Line Generator"
    PLGCloseSession
End Sub

Public Function PLGUnitsDescription() As String
    Dim master As MeasurementUnit, subUnit As MeasurementUnit
    master = ActiveModelReference.MasterUnit
    subUnit = ActiveModelReference.subUnit
    PLGUnitsDescription = "Master: " & master.label & " | Sub: " & subUnit.label
End Function

Public Function PLGGenerate(ByVal first As Double, ByVal last As Double, ByVal spacing As Double, _
        ByVal totalLength As Double, ByVal placement As Long, ByVal reverse As Boolean, _
        ByVal includeFirst As Boolean, ByVal includeLast As Boolean) As String
    Dim level As level, style As LineStyle, color As Long, weight As Long
    Dim lines As New Collection, line As LineElement, currentSource As Element
    Dim distances() As Double, n As Long, i As Long, attempted As Long, remaining As Long
    Dim p As Point3d, t As Point3d, a As Point3d, b As Point3d
    Dim reason As String, originalError As String
    On Error GoTo Failed
    PLGRequire Not mSource Is Nothing, "Select an alignment first."
    PLGRequire mModel.IsActive, "The active model changed. Cancel and run the macro again."
    PLGRequire Not ActiveModelReference.IsReadOnly, "The active model/DGN is read-only."
    ' Capture settings on Generate; do not reuse the values shown when the dialog opened.
    Set level = ActiveSettings.level
    Set style = ActiveSettings.LineStyle
    color = ActiveSettings.color
    weight = ActiveSettings.LineWeight
    PLGRequire level.ElementAccess = msdLevelElementAccessAll, _
        "The active level must allow modification/deletion so failed writes can be rolled back. Choose an unlocked writable level."
    Set currentSource = mModel.GetElementByID(mSource.ID)
    If Not PLGLoadPath(currentSource, reason) Then Err.Raise vbObjectError + 2605, , reason
    n = PLGBuildDistances(first, last, spacing, includeFirst, includeLast, distances)
    For i = 1 To n
        PLGEvaluate distances(i), reverse, p, t
        PLGEndpoints p, t, totalLength, placement, a, b
        Set line = CreateLineElement2(Nothing, a, b)
        line.color = color
        line.LineWeight = weight
        Set line.LineStyle = style
        PLGRequire Abs(line.Length - totalLength) <= PLGDistanceTolerance(), "A prepared line has the wrong length."
        lines.Add line
    Next i
    ' All geometry and all LineElements now exist in memory; only this loop writes.
    For i = 1 To lines.count
        Set line = lines(i)
        attempted = i
        ActiveModelReference.AddElement line
        ' Bentley forbids assigning a Level object before AddElement.
        Set line.level = level
        line.Rewrite
    Next i
    PLGGenerate = "Generated " & CStr(n) & " perpendicular lines at " & Format(spacing, "0.00") & _
        " master-unit spacing on level " & level.Name & "." & vbCrLf & PLGUnitsDescription()
    If includeLast Then PLGGenerate = PLGGenerate & vbCrLf & "The ending line may have a shorter final spacing."
    Exit Function
Failed:
    originalError = Err.Description
    ' Remove only this run's elements; never issue a broad Undo command.
    On Error Resume Next
    For i = attempted To 1 Step -1
        Err.Clear
        Set line = lines(i)
        If DLongToString(line.ID) <> "0" Then mModel.RemoveElement line
        If Err.Number <> 0 Then remaining = remaining + 1
    Next i
    On Error GoTo 0
    If remaining > 0 Then
        originalError = originalError & vbCrLf & "Rollback could not remove " & CStr(remaining) & _
            " element(s). Use ordinary Undo and inspect the model before retrying."
    ElseIf attempted > 0 Then
        originalError = originalError & vbCrLf & "This run's added elements were removed."
    Else
        originalError = originalError & vbCrLf & "No elements were added."
    End If
    Err.Raise vbObjectError + 2604, "Perpendicular Lines", originalError
End Function

Attribute VB_Name = "clsPerpendicularLocate"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
Implements ILocateCommandEvents
Implements IPrimitiveCommandEvents

Private mTarget As Long
Private mReverse As Boolean
Private mPreviewLength As Double
Private mPlacement As Long
Private mFirstDistance As Double
Private mFollowWithEnd As Boolean
Private mFinishing As Boolean

Public Sub ConfigurePick(ByVal target As Long, ByVal reverse As Boolean, ByVal previewLength As Double, _
        ByVal placement As Long, ByVal firstDistance As Double, ByVal followWithEnd As Boolean)
    mTarget = target
    mReverse = reverse
    mPreviewLength = previewLength
    mPlacement = placement
    mFirstDistance = firstDistance
    mFollowWithEnd = followWithEnd
End Sub

Private Sub ILocateCommandEvents_Start()
    Dim criteria As LocateCriteria
    Set criteria = CommandState.CreateLocateCriteria(False)
    CommandState.SetLocateCriteria criteria
    ShowCommand "Perpendicular Line Generator"
    ShowPrompt "Identify horizontal geometry, then accept. Reset cancels."
End Sub

Private Sub ILocateCommandEvents_LocateFilter(ByVal Element As Element, Point As Point3d, accepted As Boolean)
    On Error GoTo Rejected
    accepted = False
    If Element.ModelReference.IsAttachment Then Exit Sub
    If Not Element.ModelReference.IsActive Then Exit Sub
    Select Case Element.Type
        Case msdElementTypeLine, msdElementTypeLineString, msdElementTypeArc, _
                msdElementTypeBsplineCurve, msdElementTypeComplexString
            accepted = True
        Case Else
            ShowPrompt "Unsupported type. Native civil spirals need a Civil SDK evaluator. Select a standard linear element."
    End Select
    Exit Sub
Rejected:
    accepted = False
    ShowPrompt Err.Description
End Sub

Private Sub ILocateCommandEvents_Accept(ByVal Element As Element, Point As Point3d, ByVal View As View)
    On Error GoTo Failed
    If Not PLGBeginAlignment(Element) Then CommandState.StartLocate New clsPerpendicularLocate
    Exit Sub
Failed:
    MsgBox Err.Description, vbExclamation, "Perpendicular Line Generator"
    CommandState.StartDefaultCommand
End Sub

Private Sub ILocateCommandEvents_LocateReset()
    CommandState.StartDefaultCommand
End Sub

Private Sub ILocateCommandEvents_LocateFailed()
    ShowPrompt "No supported element found. Select a line, line string, arc, B-spline, or complex string. Reset cancels."
End Sub

Private Sub ILocateCommandEvents_Dynamics(Point As Point3d, ByVal View As View, ByVal DrawMode As MsdDrawingMode)
End Sub

Private Sub ILocateCommandEvents_Cleanup()
End Sub

Private Sub IPrimitiveCommandEvents_Start()
    Dim direction As String
    If mReverse Then direction = "Reverse" Else direction = "Forward"
    ShowCommand "Perpendicular Line Generator - Range"
    If mTarget = 1 Then
        ShowPrompt "Pick START (" & direction & ") on the alignment. Move for preview, data point to accept. Reset opens settings."
    Else
        ShowPrompt "Pick END after the start in the chosen direction. Move for preview, data point to accept. Reset opens settings."
    End If
    CommandState.EnableAccuSnap
    CommandState.StartDynamics
End Sub

Private Sub DrawLimit(ByVal distance As Double, ByVal DrawMode As MsdDrawingMode)
    Dim p As Point3d, t As Point3d, a As Point3d, b As Point3d, preview As LineElement
    PLGEvaluate distance, mReverse, p, t
    PLGEndpoints p, t, mPreviewLength, mPlacement, a, b
    Set preview = CreateLineElement2(Nothing, a, b)
    preview.Redraw DrawMode
End Sub

Private Sub IPrimitiveCommandEvents_Dynamics(Point As Point3d, ByVal View As View, ByVal DrawMode As MsdDrawingMode)
    Dim distance As Double, anchor As Point3d, prompt As String
    On Error GoTo Failed
    PLGRequire PLGPickContextValid(), "The active model changed. Reset or start the tool again."
    distance = PLGNearestDistance(Point, mReverse, anchor)
    If mTarget = 2 Then DrawLimit mFirstDistance, DrawMode
    DrawLimit distance, DrawMode
    If mTarget = 1 Then prompt = "START" Else prompt = "END"
    prompt = prompt & " geometry distance: " & Format(distance, "0.000") & " master units. Click to accept; Reset opens settings."
    If mTarget = 2 And distance <= mFirstDistance + PLGDistanceTolerance() Then
        prompt = "END must follow START in the chosen direction. Reset to change Direction or choose the full alignment."
    End If
    ShowPrompt prompt
    Exit Sub
Failed:
    ShowPrompt Err.Description
End Sub

Private Sub IPrimitiveCommandEvents_DataPoint(Point As Point3d, ByVal View As View)
    Dim distance As Double, anchor As Point3d, p As Point3d, t As Point3d
    On Error GoTo Failed
    PLGRequire PLGPickContextValid(), "The active model changed. Reset or start the tool again."
    distance = PLGNearestDistance(Point, mReverse, anchor)
    PLGEvaluate distance, mReverse, p, t
    If mTarget = 2 Then
        PLGRequire distance > mFirstDistance + PLGDistanceTolerance(), _
            "END must follow START in the chosen direction. Pick farther along, or Reset to change Direction."
    End If
    FinishPick True, distance
    Exit Sub
Failed:
    ShowPrompt Err.Description
End Sub

Private Sub FinishPick(ByVal accepted As Boolean, ByVal distance As Double)
    StopPick
    PLGFinishRangePick mTarget, accepted, distance, mFollowWithEnd
End Sub

Public Sub StopPick()
    mFinishing = True
    CommandState.StartDefaultCommand
End Sub

Private Sub IPrimitiveCommandEvents_Reset()
    FinishPick False, 0#
End Sub

Private Sub IPrimitiveCommandEvents_Cleanup()
    If Not mFinishing Then PLGCloseSession
End Sub

Private Sub IPrimitiveCommandEvents_Keyin(ByVal Keyin As String)
End Sub

Attribute VB_Name = "frmPerpendicularLines"
Attribute VB_Base = "0{BC82DE37-C9DB-430D-BF8C-1E264723A6C3}{C9914BE0-2428-4FBB-982A-02DD37483B0B}"
Attribute VB_GlobalNameSpace = False
Attribute VB_Creatable = False
Attribute VB_PredeclaredId = True
Attribute VB_Exposed = False
Attribute VB_TemplateDerived = False
Attribute VB_Customizable = False
Option Explicit

' Paste into a NEW blank UserForm named frmPerpendicularLines.
' Controls are created here; no FRX blob or VBA-project automation is needed.
Private WithEvents txtSpacing As MSForms.TextBox
Attribute txtSpacing.VB_VarHelpID = -1
Private WithEvents txtLength As MSForms.TextBox
Attribute txtLength.VB_VarHelpID = -1
Private WithEvents txtStart As MSForms.TextBox
Attribute txtStart.VB_VarHelpID = -1
Private WithEvents txtEnd As MSForms.TextBox
Attribute txtEnd.VB_VarHelpID = -1
Private WithEvents cboPlacement As MSForms.ComboBox
Attribute cboPlacement.VB_VarHelpID = -1
Private WithEvents cboDirection As MSForms.ComboBox
Attribute cboDirection.VB_VarHelpID = -1
Private WithEvents chkStart As MSForms.CheckBox
Attribute chkStart.VB_VarHelpID = -1
Private WithEvents chkEnd As MSForms.CheckBox
Attribute chkEnd.VB_VarHelpID = -1
Private WithEvents cmdGenerate As MSForms.CommandButton
Attribute cmdGenerate.VB_VarHelpID = -1
Private WithEvents cmdCancel As MSForms.CommandButton
Attribute cmdCancel.VB_VarHelpID = -1
Private WithEvents cmdPickStart As MSForms.CommandButton
Attribute cmdPickStart.VB_VarHelpID = -1
Private WithEvents cmdPickEnd As MSForms.CommandButton
Attribute cmdPickEnd.VB_VarHelpID = -1
Private WithEvents cmdFullAlignment As MSForms.CommandButton
Attribute cmdFullAlignment.VB_VarHelpID = -1
Private lblLevel As MSForms.label
Private lblUnits As MSForms.label
Private lblStatus As MSForms.label
Private lblEstimate As MSForms.label
Private mInitializing As Boolean
Private mRequestedPick As Long

Private Function AddLabel(ByVal controlName As String, ByVal caption As String, _
        ByVal x As Single, ByVal y As Single, ByVal width As Single, ByVal height As Single) As MSForms.label
    Dim label As MSForms.label
    Set label = Me.Controls.Add("Forms.Label.1", controlName, True)
    label.caption = Replace(caption, "&", "")
    If InStr(caption, "&") > 0 Then label.Accelerator = Mid$(caption, InStr(caption, "&") + 1, 1)
    label.Left = x: label.Top = y: label.width = width: label.height = height
    Set AddLabel = label
End Function

Private Function AddText(ByVal controlName As String, ByVal caption As String, _
        ByVal y As Single, ByVal value As String) As MSForms.TextBox
    Dim label As MSForms.label, box As MSForms.TextBox
    Set label = AddLabel("lbl" & controlName, caption, 18, y + 3, 220, 18)
    Set box = Me.Controls.Add("Forms.TextBox.1", controlName, True)
    box.Left = 250: box.Top = y: box.width = 230: box.height = 22
    box.value = value
    Set AddText = box
End Function

Private Sub UserForm_Initialize()
    Dim label As MSForms.label
    mInitializing = True
    Me.caption = "Perpendicular Line Generator"
    Me.width = 512: Me.height = 540
    Me.StartUpPosition = 1
    Me.Font.Name = "Segoe UI": Me.Font.Size = 10
    Set label = AddLabel("lblHeading", "PERPENDICULAR LINE GENERATOR", 18, 14, 462, 22)
    label.Font.Bold = True: label.Font.Size = 12
    Set label = AddLabel("lblDistances", "All distances use model MASTER units, measured along geometry from the chosen direction's beginning. These are NOT displayed ORD stations.", 18, 42, 462, 38)
    Set lblStatus = AddLabel("lblStatus", "Alignment: not selected", 18, 84, 462, 32)
    Set lblLevel = AddLabel("lblLevel", "Active level:", 18, 118, 462, 18)
    Set lblUnits = AddLabel("lblUnits", "Working units:", 18, 138, 462, 18)
    Set txtSpacing = AddText("txtSpacing", "Line &Spacing", 168, Format$(150#, "0.00"))
    Set txtLength = AddText("txtLength", "Total Line &Length", 198, Format$(200#, "0.00"))
    Set label = AddLabel("lblPlacement", "&Placement", 18, 231, 220, 18)
    Set cboPlacement = Me.Controls.Add("Forms.ComboBox.1", "cboPlacement", True)
    With cboPlacement
        .Left = 250: .Top = 228: .width = 230: .height = 22
        .style = fmStyleDropDownList
        .AddItem "Centered on Alignment": .AddItem "Left of Alignment": .AddItem "Right of Alignment"
        .ListIndex = 0
    End With
    Set txtStart = AddText("txtStart", "&Start Distance Along Alignment", 258, Format$(0#, "0.00"))
    Set txtEnd = AddText("txtEnd", "&End Distance", 288, "End of Alignment")
    txtStart.width = 150: txtEnd.width = 150
    Set cmdPickStart = Me.Controls.Add("Forms.CommandButton.1", "cmdPickStart", True)
    With cmdPickStart
        .caption = "Pick Start": .Left = 410: .Top = 258: .width = 70: .height = 22
    End With
    Set cmdPickEnd = Me.Controls.Add("Forms.CommandButton.1", "cmdPickEnd", True)
    With cmdPickEnd
        .caption = "Pick End": .Left = 410: .Top = 288: .width = 70: .height = 22
    End With
    Set label = AddLabel("lblDirection", "&Direction", 18, 321, 220, 18)
    Set cboDirection = Me.Controls.Add("Forms.ComboBox.1", "cboDirection", True)
    With cboDirection
        .Left = 250: .Top = 318: .width = 230: .height = 22
        .style = fmStyleDropDownList
        .AddItem "Forward": .AddItem "Reverse": .ListIndex = 0
    End With
    Set chkStart = Me.Controls.Add("Forms.CheckBox.1", "chkStart", True)
    With chkStart
        .caption = "Include Starting Line": .Left = 18: .Top = 356: .width = 220: .height = 22: .value = True
        .Accelerator = "I"
    End With
    Set chkEnd = Me.Controls.Add("Forms.CheckBox.1", "chkEnd", True)
    With chkEnd
        .caption = "Include Ending Line": .Left = 250: .Top = 356: .width = 230: .height = 22: .value = False
        .Accelerator = "N"
    End With
    Set lblEstimate = AddLabel("lblEstimate", "Estimated lines:", 18, 390, 462, 34)
    Set label = AddLabel("lblLimit", "VBA geometry only. Native civil spirals/station equations are not interpreted. Left/right follow the chosen direction. Limit: 10,000 lines.", 18, 428, 462, 36)
    Set cmdGenerate = Me.Controls.Add("Forms.CommandButton.1", "cmdGenerate", True)
    With cmdGenerate
        .caption = "Generate Lines": .Accelerator = "G"
        .Left = 250: .Top = 476: .width = 140: .height = 28: .Default = True
    End With
    Set cmdCancel = Me.Controls.Add("Forms.CommandButton.1", "cmdCancel", True)
    With cmdCancel
        .caption = "Cancel": .Left = 400: .Top = 476: .width = 80: .height = 28: .Cancel = True
    End With
    Set cmdFullAlignment = Me.Controls.Add("Forms.CommandButton.1", "cmdFullAlignment", True)
    With cmdFullAlignment
        .caption = "Full Alignment": .Accelerator = "F"
        .Left = 18: .Top = 476: .width = 130: .height = 28
    End With
    mInitializing = False
End Sub

Public Sub PrepareDialog(ByVal status As String)
    mRequestedPick = 0
    RefreshContext status
End Sub

Public Property Get RequestedPick() As Long
    RequestedPick = mRequestedPick
End Property

Public Sub ReadPickSettings(ByVal target As Long, ByRef reverse As Boolean, ByRef previewLength As Double, _
        ByRef placement As Long, ByRef firstDistance As Double)
    previewLength = ReadNumber(txtLength, "Total Line Length")
    PLGRequire previewLength > 4# * PLGDistanceTolerance(), "Total Line Length must be positive and exceed four distance tolerances."
    placement = cboPlacement.ListIndex
    PLGRequire placement >= 0 And cboDirection.ListIndex >= 0, "Choose placement and direction."
    reverse = (cboDirection.ListIndex = 1)
    If target = 2 Then
        firstDistance = ReadNumber(txtStart, "Start Distance")
        PLGRequire firstDistance >= 0# And firstDistance <= PLGPathLength(), "Start Distance is outside the geometry. Pick Start again."
    End If
End Sub

Public Sub SetPickedDistance(ByVal target As Long, ByVal distance As Double)
    If target = 1 Then
        txtStart.value = CStr(distance)
    ElseIf Abs(distance - PLGPathLength()) <= PLGDistanceTolerance() Then
        txtEnd.value = "End of Alignment"
    Else
        txtEnd.value = CStr(distance)
    End If
    RefreshEstimate
End Sub

Private Sub cmdPickStart_Click()
    mRequestedPick = 1
    Me.Hide
End Sub

Private Sub cmdPickEnd_Click()
    mRequestedPick = 2
    Me.Hide
End Sub

Private Sub cmdFullAlignment_Click()
    mInitializing = True
    txtStart.value = Format$(0#, "0.00")
    txtEnd.value = "End of Alignment"
    mInitializing = False
    RefreshEstimate
End Sub

Public Sub RefreshContext(ByVal status As String)
    lblStatus.caption = "Alignment: " & status
    lblLevel.caption = "Active level: " & ActiveSettings.level.Name & " (captured again on Generate)"
    lblUnits.caption = "Working units - " & PLGUnitsDescription()
    RefreshEstimate
End Sub

Private Function ReadNumber(box As MSForms.TextBox, ByVal field As String) As Double
    PLGRequire Len(Trim$(box.Text)) > 0, field & " is required."
    PLGRequire IsNumeric(box.Text), field & " must be a number in master units (no station notation or unit suffix)."
    ReadNumber = CDbl(box.Text)
    PLGRequire Abs(ReadNumber) <= 1000000000#, field & " must not exceed 1 billion master units."
End Function

Private Function ReadSettings(first As Double, last As Double, spacing As Double, totalLength As Double, _
        distances() As Double) As Long
    spacing = ReadNumber(txtSpacing, "Line Spacing")
    totalLength = ReadNumber(txtLength, "Total Line Length")
    PLGRequire totalLength > 4# * PLGDistanceTolerance(), "Total Line Length must be positive and exceed four distance tolerances."
    first = ReadNumber(txtStart, "Start Distance")
    If Len(Trim$(txtEnd.Text)) = 0 Or LCase$(Trim$(txtEnd.Text)) = "end of alignment" Then
        last = PLGPathLength()
    Else
        last = ReadNumber(txtEnd, "End Distance")
    End If
    PLGRequire cboPlacement.ListIndex >= 0 And cboDirection.ListIndex >= 0, "Choose placement and direction."
    ReadSettings = PLGBuildDistances(first, last, spacing, CBool(chkStart.value), CBool(chkEnd.value), distances)
End Function

Private Sub RefreshEstimate()
    Dim first As Double, last As Double, spacing As Double, totalLength As Double, distances() As Double, n As Long
    If mInitializing Then Exit Sub
    On Error GoTo Invalid
    n = ReadSettings(first, last, spacing, totalLength, distances)
    lblEstimate.caption = "Estimated lines: " & CStr(n) & " | An optional ending line can shorten the final interval."
    cmdGenerate.Enabled = True
    Exit Sub
Invalid:
    lblEstimate.caption = Err.Description
    cmdGenerate.Enabled = False
End Sub

Private Sub cmdGenerate_Click()
    Dim first As Double, last As Double, spacing As Double, totalLength As Double, distances() As Double
    Dim n As Long, result As String
    On Error GoTo Failed
    n = ReadSettings(first, last, spacing, totalLength, distances)
    cmdGenerate.Enabled = False
    result = PLGGenerate(first, last, spacing, totalLength, cboPlacement.ListIndex, _
        cboDirection.ListIndex = 1, CBool(chkStart.value), CBool(chkEnd.value))
    MsgBox result, vbInformation, "Perpendicular Line Generator"
    cmdGenerate.Enabled = True
    Me.Hide
    Exit Sub
Failed:
    MsgBox Err.Description, vbExclamation, "Perpendicular Line Generator"
    RefreshEstimate
End Sub

Private Sub cmdCancel_Click()
    Me.Hide
End Sub

Private Sub UserForm_QueryClose(Cancel As Integer, CloseMode As Integer)
    If CloseMode = vbFormControlMenu Then
        Cancel = True
        Me.Hide
    End If
End Sub

Private Sub txtSpacing_Change()
    RefreshEstimate
End Sub
Private Sub txtLength_Change()
    RefreshEstimate
End Sub
Private Sub txtStart_Change()
    RefreshEstimate
End Sub
Private Sub txtEnd_Change()
    RefreshEstimate
End Sub
Private Sub cboPlacement_Change()
    RefreshEstimate
End Sub
Private Sub cboDirection_Change()
    RefreshEstimate
End Sub
Private Sub chkStart_Click()
    RefreshEstimate
End Sub
Private Sub chkEnd_Click()
    RefreshEstimate
End Sub

Attribute VB_Name = "modPerpendicularGeometry"
Option Explicit

' Geometry distances and coordinates are in active-model master units.
' Bentley ORD 2026 MicroStationVBA.chm: BsplineCurve.FromElement,
' ComputeCurveLength, EvaluatePointAtDistance, EvaluatePointTangent.
' shortcut: evaluate exposed VBA geometry only; use a Civil SDK add-in when native spirals or station equations are required.
Public Const PLG_MAX_LINES As Long = 10000
Private Const MAX_PARTS As Long = 10000
Private Const ANGLE_TOL As Double = 0.000001
Private mCurve() As BsplineCurve
Private mLength() As Double
Private mBackwards() As Boolean
Private mCount As Long
Private mTotal As Double
Private mTolerance As Double
Private mPlaneZ As Double
Private mPlaneTolerance As Double

Public Sub PLGClearPath()
    Erase mCurve
    Erase mLength
    Erase mBackwards
    mCount = 0
    mTotal = 0#
End Sub

Public Function PLGPathLength() As Double
    PLGPathLength = mTotal
End Function

Public Function PLGDistanceTolerance() As Double
    PLGDistanceTolerance = mTolerance
End Function

Public Sub PLGRequire(ByVal condition As Boolean, ByVal message As String)
    If Not condition Then Err.Raise vbObjectError + 2601, "Perpendicular Lines", message
End Sub

Public Function PLGPointDistance(a As Point3d, b As Point3d) As Double
    PLGPointDistance = Sqr((a.x - b.x) ^ 2 + (a.y - b.y) ^ 2 + (a.Z - b.Z) ^ 2)
End Function

Private Function UnitXY(v As Point3d) As Point3d
    Dim magnitude As Double
    magnitude = Sqr(v.x * v.x + v.y * v.y)
    PLGRequire magnitude > 0#, "The geometry has a zero XY tangent (cusp or degenerate curve)."
    UnitXY = Point3dFromXYZ(v.x / magnitude, v.y / magnitude, 0#)
End Function

Private Sub SameTangent(a As Point3d, b As Point3d)
    Dim u As Point3d, v As Point3d
    u = UnitXY(a)
    v = UnitXY(b)
    PLGRequire PLGPointDistance(u, v) <= ANGLE_TOL, _
        "A checked spline knot or requested component join has a corner, cusp, or discontinuous tangent. Use smooth geometry or avoid a non-tangent component join."
End Sub

Public Function PLGLoadPath(source As Element, ByRef reason As String) As Boolean
    Dim expected As Point3d, ending As Point3d, sourceLength As Double
    On Error GoTo Failed
    PLGClearPath
    PLGRequire source.IsTraversableElement, "This element does not expose traversable VBA geometry."
    sourceLength = GetElementPathLength(source)
    PLGRequire sourceLength > 0# And sourceLength <= 1000000000#, "Alignment length must be positive and at most 1 billion master units."
    mTolerance = 2# / ActiveModelReference.UORsPerMasterUnit
    If mTolerance < sourceLength * 0.0000000001 Then mTolerance = sourceLength * 0.0000000001
    ReDim mCurve(1 To MAX_PARTS)
    ReDim mLength(1 To MAX_PARTS)
    ReDim mBackwards(1 To MAX_PARTS)
    expected = source.AsTraversableElement.PointAtDistance(0#)
    ending = source.AsTraversableElement.PointAtDistance(sourceLength)
    mPlaneZ = expected.Z
    mPlaneTolerance = Abs(mPlaneZ) * 0.00000000000001
    If mPlaneTolerance < 0.000000000001 Then mPlaneTolerance = 0.000000000001
    PLGRequire PLGPointDistance(expected, ending) > mTolerance, "Closed alignments are not supported; use an open path."
    AppendElement source, expected, 0
    PLGRequire mCount > 0, "No supported geometry components were found."
    PLGRequire PLGPointDistance(expected, ending) <= mTolerance, "Component order does not match the selected element's direction."
    PLGRequire Abs(mTotal - sourceLength) <= mTolerance, "Component lengths disagree with the selected geometry; civil/approximated geometry is not supported."
    PLGRequire mTotal > mTolerance, "Alignment is shorter than the model distance tolerance."
    reason = "Supported VBA path: " & CStr(mCount) & " component(s), length " & Format(mTotal, "0.00")
    PLGLoadPath = True
    Exit Function
Failed:
    reason = Err.Description & vbCrLf & _
        "Native ORD spirals/custom civil elements require a Civil SDK evaluator. No lines were created."
    PLGClearPath
End Function

Private Function GetElementPathLength(source As Element) As Double
    Select Case source.Type
        Case msdElementTypeLine, msdElementTypeLineString
            GetElementPathLength = source.AsLineElement.Length
        Case msdElementTypeArc
            GetElementPathLength = source.AsArcElement.Length
        Case msdElementTypeBsplineCurve
            GetElementPathLength = source.AsBsplineCurveElement.Length
        Case msdElementTypeComplexString
            GetElementPathLength = source.AsComplexStringElement.Length
        Case Else
            Err.Raise vbObjectError + 2602, , "Unsupported element type " & CStr(source.Type) & ". Its native geometry cannot be evaluated by this tool."
    End Select
End Function

Private Sub AppendElement(source As Element, expected As Point3d, ByVal depth As Long)
    Dim ee As ElementEnumerator, child As Element, vertices() As Point3d
    Dim i As Long, first As Long, last As Long, stepIndex As Long
    Dim piece As LineElement, curve As BsplineCurve
    PLGRequire depth <= 16, "Complex geometry nesting exceeds 16 levels."
    Select Case source.Type
        Case msdElementTypeComplexString
            Set ee = source.AsComplexStringElement.GetSubElements
            Do While ee.MoveNext
                Set child = ee.Current
                AppendElement child, expected, depth + 1
            Loop
        Case msdElementTypeLineString
            vertices = source.AsVertexList.GetVertices
            first = LBound(vertices): last = UBound(vertices): stepIndex = 1
            PLGRequire last > first, "The line string has fewer than two vertices."
            If PLGPointDistance(expected, vertices(first)) > mTolerance Then
                first = UBound(vertices): last = LBound(vertices): stepIndex = -1
            End If
            For i = first To last - stepIndex Step stepIndex
                Set piece = CreateLineElement2(Nothing, vertices(i), vertices(i + stepIndex))
                Set curve = New BsplineCurve
                curve.FromElement piece
                AppendCurve curve, expected
            Next i
        Case msdElementTypeLine, msdElementTypeArc, msdElementTypeBsplineCurve
            Set curve = New BsplineCurve
            curve.FromElement source
            AppendCurve curve, expected
        Case Else
            Err.Raise vbObjectError + 2602, , "Unsupported element/component type " & CStr(source.Type) & _
                ". Acceptable types: line, line string, arc, B-spline, and complex strings made only from these."
    End Select
End Sub

Private Sub AppendCurve(curve As BsplineCurve, expected As Point3d)
    Dim a As Point3d, b As Point3d, pole As Point3d
    Dim i As Long, curveLength As Double, backwards As Boolean
    PLGRequire mCount < MAX_PARTS, "Alignment exceeds 10,000 geometry components."
    PLGRequire Not curve.Closed, "Closed curves are not supported; use an open alignment."
    a = curve.EvaluatePoint(0#): b = curve.EvaluatePoint(1#)
    PLGRequire PLGPointDistance(a, b) > mTolerance, "Closed or zero-length component is not supported."
    For i = 0 To curve.PolesCount - 1
        pole = curve.pole(i)
        PLGRequire Abs(pole.Z - mPlaneZ) <= mPlaneTolerance, _
            "Only horizontal geometry is supported. A component has changing Z or a tilted plane."
    Next i
    If PLGPointDistance(expected, a) > mTolerance Then
        PLGRequire PLGPointDistance(expected, b) <= mTolerance, "Alignment components have a gap or unsupported ordering."
        backwards = True
    End If
    curveLength = curve.ComputeCurveLength
    PLGRequire curveLength > mTolerance, "A component is zero length or below model resolution."
    ' Reject internal spline discontinuities instead of choosing an arbitrary derivative.
    CheckSplineKnots curve
    mCount = mCount + 1
    Set mCurve(mCount) = curve
    mLength(mCount) = curveLength
    mBackwards(mCount) = backwards
    mTotal = mTotal + curveLength
    If backwards Then expected = a Else expected = b
End Sub

Private Sub CheckSplineKnots(curve As BsplineCurve)
    Dim i As Long, k As Double, h As Double, leftK As Double, rightK As Double
    Dim a As Point3d, b As Point3d, ta As Point3d, tb As Point3d
    For i = 0 To curve.KnotsCount - 1
        k = curve.Knot(i)
        If k > 0# And k < 1# Then
            leftK = 0#: rightK = 1#
            If i > 0 Then
                If curve.Knot(i - 1) < k Then leftK = curve.Knot(i - 1)
            End If
            If i < curve.KnotsCount - 1 Then
                If curve.Knot(i + 1) > k Then rightK = curve.Knot(i + 1)
            End If
            h = (k - leftK) * 0.00000001
            If h > (rightK - k) * 0.00000001 Then h = (rightK - k) * 0.00000001
            PLGRequire k - h < k And k + h > k, "Spline knot intervals are too small to evaluate reliably."
            a = curve.EvaluatePointTangent(ta, k - h)
            b = curve.EvaluatePointTangent(tb, k + h)
            SameTangent ta, tb
            ' Compare each side with its limit; do not mistake a gap for a curve.
            a = curve.EvaluatePoint(k)
            b = curve.EvaluatePoint(k - h * 0.01)
            PLGRequire PLGPointDistance(a, b) <= mTolerance, "Spline has a discontinuous internal knot."
            b = curve.EvaluatePoint(k + h * 0.01)
            PLGRequire PLGPointDistance(a, b) <= mTolerance, "Spline has a discontinuous internal knot."
        End If
    Next i
End Sub

Private Sub EvaluatePart(ByVal index As Long, ByVal distance As Double, p As Point3d, t As Point3d)
    Dim parameter As Double, checkPoint As Point3d, residual As Double
    If mBackwards(index) Then distance = mLength(index) - distance
    If distance <= 0# Then
        parameter = 0#: p = mCurve(index).EvaluatePoint(0#)
    ElseIf distance >= mLength(index) Then
        parameter = 1#: p = mCurve(index).EvaluatePoint(1#)
    Else
        p = mCurve(index).EvaluatePointAtDistance(parameter, distance, 0#, 0.000000000001)
    End If
    PLGRequire parameter >= 0# And parameter <= 1#, "Curve evaluator returned an invalid parameter."
    residual = Abs(mCurve(index).ComputeCurveLength(0#, parameter) - distance)
    PLGRequire residual <= mTolerance, "Curve distance inversion failed its independent length check."
    checkPoint = mCurve(index).EvaluatePointTangent(t, parameter)
    PLGRequire PLGPointDistance(p, checkPoint) <= mTolerance, "Curve point and tangent evaluators disagree."
    t = UnitXY(t)
    If mBackwards(index) Then t = Point3dFromXYZ(-t.x, -t.y, 0#)
End Sub

Public Sub PLGEvaluate(ByVal distance As Double, ByVal reverse As Boolean, p As Point3d, t As Point3d)
    Dim i As Long, accumulated As Double, partDistance As Double
    Dim otherPoint As Point3d, otherTangent As Point3d
    PLGRequire mCount > 0, "No alignment geometry is loaded."
    PLGRequire distance >= 0# And distance <= mTotal, "Distance is outside the geometry."
    If reverse Then distance = mTotal - distance
    For i = 1 To mCount
        partDistance = distance - accumulated
        If partDistance <= mLength(i) Or i = mCount Then
            If partDistance < 0# Then partDistance = 0#
            If partDistance > mLength(i) Then partDistance = mLength(i)
            EvaluatePart i, partDistance, p, t
            If partDistance <= mTolerance And i > 1 Then
                EvaluatePart i - 1, mLength(i - 1), otherPoint, otherTangent
                SameTangent t, otherTangent
            End If
            If mLength(i) - partDistance <= mTolerance And i < mCount Then
                EvaluatePart i + 1, 0#, otherPoint, otherTangent
                SameTangent t, otherTangent
            End If
            If reverse Then t = Point3dFromXYZ(-t.x, -t.y, 0#)
            Exit Sub
        End If
        accumulated = accumulated + mLength(i)
    Next i
End Sub

Public Function PLGNearestDistance(cursor As Point3d, ByVal reverse As Boolean, anchor As Point3d) As Double
    Dim i As Long, bestIndex As Long, parameter As Double, accumulated As Double, partDistance As Double
    Dim distances() As Double, pathDistances() As Double, points() As Point3d
    Dim checkPoint As Point3d, rotation As Matrix3d, measured As Double
    PLGRequire mCount > 0, "No alignment geometry is loaded."
    ReDim distances(1 To mCount)
    ReDim pathDistances(1 To mCount)
    ReDim points(1 To mCount)
    rotation = Matrix3dIdentity
    For i = 1 To mCount
        distances(i) = mCurve(i).ComputeMinimumDistance(points(i), parameter, cursor, rotation)
        PLGRequire parameter >= 0# And parameter <= 1#, "Closest-point evaluator returned a parameter outside the curve."
        checkPoint = mCurve(i).EvaluatePoint(parameter)
        PLGRequire PLGPointDistance(points(i), checkPoint) <= mTolerance, "Closest-point and curve evaluators disagree."
        measured = Sqr((cursor.x - points(i).x) ^ 2 + (cursor.y - points(i).y) ^ 2)
        PLGRequire Abs(measured - distances(i)) <= mTolerance, "Closest-point evaluator returned an inconsistent XY distance."
        partDistance = mCurve(i).ComputeCurveLength(0#, parameter)
        If mBackwards(i) Then partDistance = mLength(i) - partDistance
        pathDistances(i) = accumulated + partDistance
        If bestIndex = 0 Then
            bestIndex = i
        ElseIf distances(i) < distances(bestIndex) Then
            bestIndex = i
        End If
        accumulated = accumulated + mLength(i)
    Next i
    For i = 1 To mCount
        If distances(i) <= distances(bestIndex) + mTolerance Then
            PLGRequire Abs(pathDistances(i) - pathDistances(bestIndex)) <= mTolerance, _
                "This pick is equally close to different alignment locations. Move away from the crossing or overlap."
        End If
    Next i
    ' shortcut: Bentley returns one minimum per B-spline; use typed distances when that component has multiple equally close locations.
    PLGNearestDistance = pathDistances(bestIndex)
    If reverse Then PLGNearestDistance = mTotal - PLGNearestDistance
    If PLGNearestDistance <= mTolerance Then PLGNearestDistance = 0#
    If mTotal - PLGNearestDistance <= mTolerance Then PLGNearestDistance = mTotal
    anchor = points(bestIndex)
End Function

Public Function PLGBuildDistances(ByVal first As Double, ByVal last As Double, ByVal spacing As Double, _
        ByVal includeFirst As Boolean, ByVal includeLast As Boolean, distances() As Double) As Long
    Dim k As Long, maxK As Long, n As Long, d As Double, ratio As Double
    PLGRequire mCount > 0, "No alignment geometry is loaded."
    PLGRequire spacing > 4# * mTolerance And spacing <= 1000000000#, "Spacing must be positive, exceed four distance tolerances, and be at most 1 billion master units."
    PLGRequire first >= 0# And last <= mTotal And last - first > mTolerance, "Require 0 <= start < end <= geometry length."
    ratio = (last - first) / spacing
    PLGRequire ratio <= PLG_MAX_LINES + 1#, "More than 10,000 lines requested. Increase spacing or shorten the range."
    maxK = CLng(Fix(ratio))
    ReDim distances(1 To PLG_MAX_LINES + 2)
    For k = 0 To maxK
        d = first + CDbl(k) * spacing
        If d < last - mTolerance And (k > 0 Or includeFirst) Then
            n = n + 1: distances(n) = d
        End If
    Next k
    If includeLast Then n = n + 1: distances(n) = last
    PLGRequire n > 0, "The settings request no lines. Include an endpoint or reduce spacing."
    PLGRequire n <= PLG_MAX_LINES, "More than 10,000 lines requested. Increase spacing or shorten the range."
    ReDim Preserve distances(1 To n)
    PLGBuildDistances = n
End Function

Public Sub PLGEndpoints(p As Point3d, t As Point3d, ByVal totalLength As Double, _
        ByVal placement As Long, a As Point3d, b As Point3d)
    Dim leftDistance As Double, rightDistance As Double
    PLGRequire totalLength > 4# * mTolerance And totalLength <= 1000000000#, "Line length must be positive, exceed four distance tolerances, and be at most 1 billion master units."
    Select Case placement
        Case 0: leftDistance = totalLength / 2#: rightDistance = totalLength / 2#
        Case 1: leftDistance = totalLength
        Case 2: rightDistance = totalLength
        Case Else: Err.Raise vbObjectError + 2603, , "Choose a placement option."
    End Select
    a = Point3dFromXYZ(p.x - t.y * leftDistance, p.y + t.x * leftDistance, p.Z)
    b = Point3dFromXYZ(p.x + t.y * rightDistance, p.y - t.x * rightDistance, p.Z)
    PLGRequire Abs(PLGPointDistance(a, b) - totalLength) <= mTolerance, "Line length failed the coordinate precision check."
End Sub
