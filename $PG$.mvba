Attribute VB_Name = "Mod_PG_"
Option Explicit

Public Sub Bmr_PG_AllSheets()

    Dim sheetNames As Collection
    Dim model As ModelReference
    Dim sheetName As Variant

    Set sheetNames = New Collection

    'Collect model names before activating them.
    For Each model In ActiveDesignFile.Models
        If model.Type = msdModelTypeSheet Then
            sheetNames.Add model.Name
        End If
    Next model

    For Each sheetName In sheetNames
        Set model = ActiveDesignFile.Models.Item(CStr(sheetName))
        model.Activate
        DoEvents

        Bmr_PG_
        DoEvents
    Next sheetName

    CadInputQueue.SendCommand "FILEDESIGN SAVESETTINGS"

End Sub

Public Sub Bmr_PG_()

    Dim startPoint As Point3d
    Dim point As Point3d
    Dim point2 As Point3d
    Dim lngTemp As Long
    Dim oMessage As CadInputMessage

    CadInputQueue.SendCommand "TEXTEDITOR MODIFY"

    CadInputQueue.SendTentativePoint _
        Point3dFromXYZ( _
            2.72003933216445, _
            5.69749374840444E-02, _
            0#), _
        1

    startPoint.X = 2.71811666666668
    startPoint.Y = 5.76158761582048E-02
    startPoint.Z = 0#

    point.X = startPoint.X
    point.Y = startPoint.Y
    point.Z = startPoint.Z

    CadInputQueue.SendAdjustedDataPoint point, 1

    CadInputQueue.SendKeyin _
        "TEXTEDITOR PLAYCOMMAND INSERT_TEXT ""$PG$"""

    point.X = startPoint.X + 0.805414879261533
    point.Y = startPoint.Y + 0.130507147480806
    point.Z = startPoint.Z

    CadInputQueue.SendDataPoint point, 1

    CommandState.StartDefaultCommand

End Sub
