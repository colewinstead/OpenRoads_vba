Attribute VB_Name = "ModXS_Stamp"
Sub BmrXS_Stamp()
    Dim startPoint As Point3d
    Dim point As Point3d, point2 As Point3d
    Dim lngTemp As Long
    Dim oMessage As CadInputMessage

'   Send a tentative point
'   Coordinates are in master units
    CadInputQueue.SendTentativePoint Point3dFromXYZ(2.72189782460253, 5.76888723563094E-02, 0#), 1

'   Coordinates are in master units
    startPoint.X = 2.71811666666668
    startPoint.Y = 5.76158761582048E-02
    startPoint.Z = 0#

'   Send a data point to the current command
    point.X = startPoint.X
    point.Y = startPoint.Y
    point.Z = startPoint.Z
    CadInputQueue.SendAdjustedDataPoint point, 1

    point.X = startPoint.X - 0.404806100308599
    point.Y = startPoint.Y + 9.44535593775837E-04
    point.Z = startPoint.Z
    CadInputQueue.SendDataPoint point, 1

    point.X = startPoint.X - 0.41003322941194
    point.Y = startPoint.Y + 4.43069317646083E-03
    point.Z = startPoint.Z
    CadInputQueue.SendDataPoint point, 1

    point.X = startPoint.X - 0.41003322941194
    point.Y = startPoint.Y + 4.43069317646083E-03
    point.Z = startPoint.Z
    CadInputQueue.SendDataPoint point, 1

'   Send a keyin that can be a command string
    CadInputQueue.SendKeyin "TEXTEDITOR MODIFY"

'   XX-MacroComment_Header-XX

'   XX-MacroComment_InsertText-XX

    CadInputQueue.SendKeyin "TEXTEDITOR PLAYCOMMAND INSERT_TEXT ""**s"""

'   XX-MacroComment_KeyDownPerCharacter-XX

'   Start a command
    CadInputQueue.SendCommand "TEXTEDITOR PLAYCOMMAND KEY_DOWN KEY_CODE 0x02 CONTROL_KEY_STATE UP SHIFT_KEY_STATE UP ALT_KEY_STATE UP"

    CadInputQueue.SendKeyin "TEXTEDITOR PLAYCOMMAND INSERT_TEXT ""SOUTH REALIGNMENT ALTERNATE**"""

    point.X = startPoint.X - 0.242765098105042
    point.Y = startPoint.Y + 0.125574669174765
    point.Z = startPoint.Z
    CadInputQueue.SendDataPoint point, 1

    point.X = startPoint.X - 0.250605791760053
    point.Y = startPoint.Y + 8.98415539522434E-02
    point.Z = startPoint.Z
    CadInputQueue.SendDataPoint point, 1

    CommandState.StartDefaultCommand
End Sub

Sub XS_Stamp_AllSheets()

    Dim oModel As ModelReference

    ' Loop through all models in the active DGN
    For Each oModel In ActiveDesignFile.Models

        ' Only run on sheet models
        If oModel.Type = msdModelTypeSheet Then

            oModel.Activate   ' make this sheet active

            ' Call the recorded macro that does the delete on this sheet
            BmrXS_Stamp

        End If

    Next oModel

    ' Save settings after all changes
    CadInputQueue.SendCommand "FILEDESIGN SAVESETTINGS"

   
End Sub
