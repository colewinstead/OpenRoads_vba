Attribute VB_Name = "ModSH_ID_TO_WK_NO"
Sub BmrSH_ID_TO_WK_NO()
    Dim startPoint As Point3d
    Dim point As Point3d, point2 As Point3d
    Dim lngTemp As Long
    Dim oMessage As CadInputMessage

'   Start a command
    CadInputQueue.SendCommand "TEXTEDITOR MODIFY"

'   Send a tentative point
'   Coordinates are in master units
    CadInputQueue.SendTentativePoint Point3dFromXYZ(2.71814713676588, 0.124591723642546, 0#), 1

'   Coordinates are in master units
    startPoint.X = 2.71801666666667
    startPoint.Y = 0.124315876158204
    startPoint.Z = 0#

'   Send a data point to the current command
    point.X = startPoint.X
    point.Y = startPoint.Y
    point.Z = startPoint.Z
    CadInputQueue.SendAdjustedDataPoint point, 1

'   XX-MacroComment_Header-XX

'   XX-MacroComment_InsertText-XX

'   Send a keyin that can be a command string
    CadInputQueue.SendKeyin "TEXTEDITOR PLAYCOMMAND INSERT_TEXT ""w"""

'   XX-MacroComment_KeyDownPerCharacter-XX

    CadInputQueue.SendCommand "TEXTEDITOR PLAYCOMMAND KEY_DOWN KEY_CODE 0x02 CONTROL_KEY_STATE UP SHIFT_KEY_STATE UP ALT_KEY_STATE UP"

    CadInputQueue.SendKeyin "TEXTEDITOR PLAYCOMMAND INSERT_TEXT ""WK. NO."""

    point.X = startPoint.X + 0.018297791598084
    point.Y = startPoint.Y + 3.19526304354426E-02
    point.Z = startPoint.Z
    CadInputQueue.SendDataPoint point, 1

    CommandState.StartDefaultCommand
End Sub
