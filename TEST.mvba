Attribute VB_Name = "ModTEST"
Sub BmrTEST()
    Dim startPoint As Point3d
    Dim point As Point3d, point2 As Point3d
    Dim lngTemp As Long
    Dim oMessage As CadInputMessage

'   Coordinates are in master units
    startPoint.X = 2.73368890464626
    startPoint.Y = 0.417978090237162
    startPoint.Z = 0#

'   Send a data point to the current command
    point.X = startPoint.X
    point.Y = startPoint.Y
    point.Z = startPoint.Z
    CadInputQueue.SendDataPoint point, 1

    point.X = startPoint.X
    point.Y = startPoint.Y
    point.Z = startPoint.Z
    CadInputQueue.SendDataPoint point, 1

'   Send a keyin that can be a command string
    CadInputQueue.SendKeyin "TEXTEDITOR MODIFY"

'   XX-MacroComment_Header-XX

'   Start a command
    CadInputQueue.SendCommand "TEXTEDITOR PLAYCOMMAND CLEAR_ANCHOR_CARET"

    CadInputQueue.SendCommand "TEXTEDITOR PLAYCOMMAND SET_INSERT_CARET LINE 0 CHARACTER 4"

    CadInputQueue.SendCommand "TEXTEDITOR PLAYCOMMAND SET_ANCHOR_CARET LINE 0 CHARACTER 4"

    CadInputQueue.SendCommand "TEXTEDITOR PLAYCOMMAND SET_INSERT_CARET LINE 0 CHARACTER 3"

    CadInputQueue.SendCommand "TEXTEDITOR PLAYCOMMAND SET_INSERT_CARET LINE 0 CHARACTER 2"

    CadInputQueue.SendCommand "TEXTEDITOR PLAYCOMMAND SET_INSERT_CARET LINE 0 CHARACTER 1"

    CadInputQueue.SendCommand "TEXTEDITOR PLAYCOMMAND SET_INSERT_CARET LINE 0 CHARACTER 0"

'   XX-MacroComment_InsertText-XX

    CadInputQueue.SendKeyin "TEXTEDITOR PLAYCOMMAND INSERT_TEXT ""s"""

'   XX-MacroComment_KeyDownPerCharacter-XX

    CadInputQueue.SendCommand "TEXTEDITOR PLAYCOMMAND KEY_DOWN KEY_CODE 0x02 CONTROL_KEY_STATE UP SHIFT_KEY_STATE UP ALT_KEY_STATE UP"

    CadInputQueue.SendKeyin "TEXTEDITOR PLAYCOMMAND INSERT_TEXT ""SR 32 BRIDGE 83.6"""

    point.X = startPoint.X + 0.21825281696686
    point.Y = startPoint.Y + 0.334393919770742
    point.Z = startPoint.Z
    CadInputQueue.SendDataPoint point, 1

    point.X = startPoint.X + 0.222831547392739
    point.Y = startPoint.Y + 0.375620567413711
    point.Z = startPoint.Z
    CadInputQueue.SendDataPoint point, 1

    CommandState.StartDefaultCommand
End Sub
