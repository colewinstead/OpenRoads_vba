Attribute VB_Name = "BmrsettingsModalHandler"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Implements IModalDialogEvents
Private Sub IModalDialogEvents_OnDialogClosed(ByVal DialogBoxName As String, ByVal DialogResult As MsdDialogBoxResult)

End Sub

Private Sub IModalDialogEvents_OnDialogOpened(ByVal DialogBoxName As String, DialogResult As MsdDialogBoxResult)

    If DialogBoxName = "Attachment Properties: isd.dgn" Then

    '   Remove the following line to let the user close the dialog box.
        DialogResult = msdDialogBoxResultCancel

    End If  ' Attachment Properties: isd.dgn

End Sub

Attribute VB_Name = "Modsettings"
Sub Bmrsettings()
    Dim startPoint As Point3d
    Dim point As Point3d, point2 As Point3d
    Dim lngTemp As Long
    Dim oMessage As CadInputMessage

    Dim modalHandler As New BmrsettingsModalHandler
    AddModalDialogEventsHandler modalHandler

'   The following statement opens modal dialog "Attachment Properties: isd.dgn"

    RemoveModalDialogEventsHandler modalHandler
    CommandState.StartDefaultCommand
End Sub
