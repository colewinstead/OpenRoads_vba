Attribute VB_Name = "Modspec_d_ft_edit"
Sub Bmrspec_d_ft_edit()
    Dim startPoint As Point3d
    Dim point As Point3d, point2 As Point3d
    Dim lngTemp As Long
    Dim oMessage As CadInputMessage

'   Start a command
    CadInputQueue.SendCommand "TEXTEDITOR MODIFY"

'   Send a tentative point
'   Coordinates are in master units
    CadInputQueue.SendTentativePoint Point3dFromXYZ(-2137048.41746437, -2137350.71744672, 0#), 1

'   Coordinates are in master units
    startPoint.X = -2137065.89908272
    startPoint.Y = -2137355.9368679
    startPoint.Z = 0#

'   Send a data point to the current command
    point.X = startPoint.X
    point.Y = startPoint.Y
    point.Z = startPoint.Z
    CadInputQueue.SendAdjustedDataPoint point, 1

'   XX-MacroComment_Header-XX

    CadInputQueue.SendCommand "TEXTEDITOR PLAYCOMMAND CHANGE_STYLE SET_PROPERTIES FONT RSC ""001_RWD_Working"""

    point.X = startPoint.X - 47.1638960554264
    point.Y = startPoint.Y + 29.7457964564674
    point.Z = startPoint.Z
    CadInputQueue.SendDataPoint point, 1

    CadInputQueue.SendCommand "ACTIVE TEXT"

    CadInputQueue.SendCommand "TEXTEDITOR MODIFY"

    CadInputQueue.SendTentativePoint Point3dFromXYZ(-2137050.78977683, -2137396.80329705, 0#), 1

    point.X = startPoint.X + 7.7531591327861
    point.Y = startPoint.Y - 45.1665763328783
    point.Z = startPoint.Z
    CadInputQueue.SendAdjustedDataPoint point, 1

    CadInputQueue.SendCommand "TEXTEDITOR PLAYCOMMAND CHANGE_STYLE SET_PROPERTIES FONT RSC ""001_RWD_Working"""

    point.X = startPoint.X - 45.9777398277074
    point.Y = startPoint.Y + 31.5259365984239
    point.Z = startPoint.Z
    CadInputQueue.SendDataPoint point, 1

    point.X = startPoint.X - 45.9777398277074
    point.Y = startPoint.Y + 31.5259365984239
    point.Z = startPoint.Z
    CadInputQueue.SendDataPoint point, 1

    CommandState.StartDefaultCommand
End Sub
