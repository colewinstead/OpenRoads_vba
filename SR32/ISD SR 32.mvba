Attribute VB_Name = "ModISD_SR_32"
Sub BmrISD_SR_32()
    Dim startPoint As Point3d
    Dim point As Point3d, point2 As Point3d
    Dim lngTemp As Long
    Dim oMessage As CadInputMessage

'   Start a command
    CadInputQueue.SendCommand "TEXTEDITOR MODIFY"

'   Send a tentative point
'   Coordinates are in master units
    CadInputQueue.SendTentativePoint Point3dFromXYZ(2.73939763609842, 5.96869621922619E-02, 0#), 1

'   Coordinates are in master units
    startPoint.X = 2.71811666666668
    startPoint.Y = 5.76158761582048E-02
    startPoint.Z = 0#

'   Send a data point to the current command
    point.X = startPoint.X
    point.Y = startPoint.Y
    point.Z = startPoint.Z
    CadInputQueue.SendAdjustedDataPoint point, 1

'   XX-MacroComment_Header-XX

'   XX-MacroComment_KeyDownPerCharacter-XX

    CadInputQueue.SendCommand "TEXTEDITOR PLAYCOMMAND KEY_DOWN KEY_CODE 0x2C CONTROL_KEY_STATE DOWN SHIFT_KEY_STATE UP ALT_KEY_STATE UP"

    CadInputQueue.SendCommand "TEXTEDITOR PLAYCOMMAND COPY"

'   XX-MacroComment_InsertText-XX

'   Send a keyin that can be a command string
    CadInputQueue.SendKeyin "TEXTEDITOR PLAYCOMMAND INSERT_TEXT ""$PG$"""

    point.X = startPoint.X + 0.245473608181464
    point.Y = startPoint.Y + 0.278804023109602
    point.Z = startPoint.Z
    CadInputQueue.SendDataPoint point, 1

    CadInputQueue.SendTentativePoint Point3dFromXYZ(2.71730566074717, 0.104717469704555, 0#), 1

    point.X = startPoint.X - 1.00000000010869E-04
    point.Y = startPoint.Y + 4.86999999999994E-02
    point.Z = startPoint.Z
    CadInputQueue.SendAdjustedDataPoint point, 1

'   XX-MacroComment_KeyDownPerCharacter-XX

    CadInputQueue.SendCommand "TEXTEDITOR PLAYCOMMAND KEY_DOWN KEY_CODE 0x2C CONTROL_KEY_STATE DOWN SHIFT_KEY_STATE UP ALT_KEY_STATE UP"

    CadInputQueue.SendCommand "TEXTEDITOR PLAYCOMMAND PASTE"

    point.X = startPoint.X + 0.196380329623131
    point.Y = startPoint.Y + 0.20839268409038
    point.Z = startPoint.Z
    CadInputQueue.SendDataPoint point, 1

    CadInputQueue.SendTentativePoint Point3dFromXYZ(2.72548787384022, 0.364256940275406, 0#), 1

    point.X = startPoint.X - 1.16666666677645E-04
    point.Y = startPoint.Y + 0.33557897312792
    point.Z = startPoint.Z
    CadInputQueue.SendAdjustedDataPoint point, 1

'   XX-MacroComment_KeyDownPerCharacter-XX

    CadInputQueue.SendCommand "TEXTEDITOR PLAYCOMMAND KEY_DOWN KEY_CODE 0x2C CONTROL_KEY_STATE DOWN SHIFT_KEY_STATE UP ALT_KEY_STATE UP"

    CadInputQueue.SendKeyin "TEXTEDITOR PLAYCOMMAND INSERT_TEXT ""DRIVEWAY S"""

'   XX-MacroComment_KeyDownPerCharacter-XX

    CadInputQueue.SendCommand "TEXTEDITOR PLAYCOMMAND KEY_DOWN KEY_CODE 0x02 CONTROL_KEY_STATE UP SHIFT_KEY_STATE UP ALT_KEY_STATE UP"

    CadInputQueue.SendKeyin "TEXTEDITOR PLAYCOMMAND INSERT_TEXT ""ISD"""

'   XX-MacroComment_KeyDownPerCharacter-XX

    CadInputQueue.SendCommand "TEXTEDITOR PLAYCOMMAND KEY_DOWN KEY_CODE 0x06 CONTROL_KEY_STATE UP SHIFT_KEY_STATE UP ALT_KEY_STATE UP"

    CadInputQueue.SendKeyin "TEXTEDITOR PLAYCOMMAND INSERT_TEXT ""STA. """

    CadInputQueue.SendCommand "TEXTEDITOR PLAYCOMMAND PASTE"

    point.X = startPoint.X + 2.45538546689636E-02
    point.Y = startPoint.Y + 0.309097273617872
    point.Z = startPoint.Z
    CadInputQueue.SendDataPoint point, 1

    point.X = startPoint.X + 0.251665497939634
    point.Y = startPoint.Y + 0.526125898255868
    point.Z = startPoint.Z
    CadInputQueue.SendDataPoint point, 1

    CommandState.StartDefaultCommand
End Sub
Sub BmrSR32_ISD_AllSheets()

    Dim oModel As ModelReference

    ' Loop through all models in the active DGN
    For Each oModel In ActiveDesignFile.Models

        ' Only run on sheet models
        If oModel.Type = msdModelTypeSheet Then

            oModel.Activate  ' make this sheet active

            ' Call the recorded macro that edits the field on this sheet
            BmrISD_SR_32

        End If

    Next oModel

    ' Save settings after all changes
    CadInputQueue.SendCommand "FILEDESIGN SAVESETTINGS"

    MsgBox "Finished changing sheet numbers to $PG$ on all sheet models.", vbInformation

End Sub
