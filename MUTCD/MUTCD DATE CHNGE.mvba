Attribute VB_Name = "ModMUTCD_DATE_CHNGE"
Sub BmrMUTCD_DATE_CHNGE()
    Dim startPoint As Point3d
    Dim point As Point3d, point2 As Point3d
    Dim lngTemp As Long
    Dim oMessage As CadInputMessage

'   Start a command
    CadInputQueue.SendCommand "MDL KEYIN FINDREPLACETEXT CHANGE DIALOGTEXT"

'   Send a keyin that can be a command string
    CadInputQueue.SendKeyin "FIND DIALOG SEARCHINCELLS True"

    CadInputQueue.SendKeyin "FIND DIALOG PAN True"

    CadInputQueue.SendKeyin "FIND DIALOG ZOOM True"

    CadInputQueue.SendKeyin "FIND DIALOG ZOOMLEVEL 14"

    CadInputQueue.SendKeyin "FIND DIALOG SEARCHSTRING M5-1R"

    CadInputQueue.SendKeyin "FIND DIALOG SEARCHSTRING 12/17/25"

    CadInputQueue.SendKeyin "FIND DIALOG REPLACESTRING 12/18/25"

    CadInputQueue.SendKeyin "CHANGE TEXT FIND"

    CadInputQueue.SendKeyin "CHANGE TEXT CHANGE"

    CommandState.StartDefaultCommand
End Sub
Sub TEXT_CHANGE_AllSheets()

    Dim oModel As ModelReference

    ' Loop through all models in the active DGN
    For Each oModel In ActiveDesignFile.Models

        ' Only run on sheet models
        If oModel.Type = msdModelTypeSheet Then

            oModel.Activate   ' make this sheet active

            ' Call the recorded macro that does the delete on this sheet
            BmrMUTCD_DATE_CHNGE

        End If

    Next oModel

    ' Save settings after all changes
    CadInputQueue.SendCommand "FILEDESIGN SAVESETTINGS"

    MsgBox "Finished changing the title on all sheet models.", vbInformation

End Sub
