Attribute VB_Name = "ModXS_STAMP4"
Sub BmrXS_STAMP4()
    Dim startPoint As Point3d
    Dim point As Point3d, point2 As Point3d
    Dim lngTemp As Long
    Dim oMessage As CadInputMessage

'   Start a command
    CadInputQueue.SendCommand "COPY ICON"

'   Send a tentative point
'   Coordinates are in master units
    CadInputQueue.SendTentativePoint Point3dFromXYZ(2.71252049187468, 5.88696503197662E-02, 0#), 1

'   Coordinates are in master units
    startPoint.X = 2.71811666666668
    startPoint.Y = 5.76158761582048E-02
    startPoint.Z = 0#

'   Send a data point to the current command
    point.X = startPoint.X
    point.Y = startPoint.Y
    point.Z = startPoint.Z
    CadInputQueue.SendAdjustedDataPoint point, 1

    point.X = startPoint.X - 0.328580568458228
    point.Y = startPoint.Y + 1.56610827242873E-04
    point.Z = startPoint.Z
    CadInputQueue.SendDataPoint point, 1

    CadInputQueue.SendCommand "MDL KEYIN PSELECT CHOOSE ELEMENT"

    CadInputQueue.SendCommand "TEXTEDITOR MODIFY"

    CadInputQueue.SendTentativePoint Point3dFromXYZ(2.38021396800076, 6.05153953212439E-02, 0#), 1

    point.X = startPoint.X - 0.328580568458228
    point.Y = startPoint.Y + 1.56610827242873E-04
    point.Z = startPoint.Z
    CadInputQueue.SendAdjustedDataPoint point, 1

'   XX-MacroComment_Header-XX

'   XX-MacroComment_InsertText-XX

'   Send a keyin that can be a command string
    CadInputQueue.SendKeyin "TEXTEDITOR PLAYCOMMAND INSERT_TEXT ""**NORTH REALIGNMENT ALTERNATE**"""

    point.X = startPoint.X - 0.256745329799016
    point.Y = startPoint.Y + 0.139496354285692
    point.Z = startPoint.Z
    CadInputQueue.SendDataPoint point, 1

    CommandState.StartDefaultCommand
End Sub
Sub XS_Stamp_AllSheets()

    Dim oModel As ModelReference

    ' Loop through all models in the active DGN
    For Each oModel In ActiveDesignFile.Models

        ' Only run on sheet models
        If oModel.Type = msdModelTypeSheet Then

            oModel.Activate   ' make this sheet active

            ' Call the recorded macro that does the delete on this sheet
            BmrXS_STAMP4

        End If

    Next oModel

    ' Save settings after all changes
    CadInputQueue.SendCommand "FILEDESIGN SAVESETTINGS"

   
End Sub
