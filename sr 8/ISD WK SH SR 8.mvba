Attribute VB_Name = "ModISD_WK_SH_SR_8"
Sub BmrISD_WK_SH_SR_8()
    Dim startPoint As Point3d
    Dim point As Point3d, point2 As Point3d
    Dim lngTemp As Long
    Dim oMessage As CadInputMessage

'   Start a command
    CadInputQueue.SendCommand "TEXTEDITOR MODIFY"

'   Send a tentative point
'   Coordinates are in master units
    CadInputQueue.SendTentativePoint Point3dFromXYZ(2.722702859126, 0.391913981743834, 0#), 1

'   Coordinates are in master units
    startPoint.X = 2.718
    startPoint.Y = 0.393194849286125
    startPoint.Z = 0#

'   Send a data point to the current command
    point.X = startPoint.X
    point.Y = startPoint.Y
    point.Z = startPoint.Z
    CadInputQueue.SendAdjustedDataPoint point, 1

'   XX-MacroComment_Header-XX

'   XX-MacroComment_InsertText-XX

'   Send a keyin that can be a command string
    CadInputQueue.SendKeyin "TEXTEDITOR PLAYCOMMAND INSERT_TEXT ""INTERSECTION SIGHT DISTANCE"""

    point.X = startPoint.X + 0.200497687199555
    point.Y = startPoint.Y + 8.76288342996156E-02
    point.Z = startPoint.Z
    CadInputQueue.SendDataPoint point, 1

    CadInputQueue.SendTentativePoint Point3dFromXYZ(2.72150166386174, 0.10716263935827, 0#), 1

    point.X = startPoint.X + 1.66666666667759E-05
    point.Y = startPoint.Y - 0.286878973127921
    point.Z = startPoint.Z
    CadInputQueue.SendAdjustedDataPoint point, 1

    CadInputQueue.SendKeyin "TEXTEDITOR PLAYCOMMAND INSERT_TEXT ""ISD-"""

    point.X = startPoint.X + 0.183680953499986
    point.Y = startPoint.Y - 0.180301753683426
    point.Z = startPoint.Z
    CadInputQueue.SendDataPoint point, 1

    CadInputQueue.SendTentativePoint Point3dFromXYZ(2.72991003071153, 5.79018586080249E-02, 0#), 1

    point.X = startPoint.X + 1.16666666677645E-04
    point.Y = startPoint.Y - 0.33557897312792
    point.Z = startPoint.Z
    CadInputQueue.SendAdjustedDataPoint point, 1

    CadInputQueue.SendKeyin "TEXTEDITOR PLAYCOMMAND INSERT_TEXT ""$PG$"""

    point.X = startPoint.X + 0.189686929821261
    point.Y = startPoint.Y - 0.13104097293318
    point.Z = startPoint.Z
    CadInputQueue.SendDataPoint point, 1

    CommandState.StartDefaultCommand
End Sub
Sub Wrapper_AllSheets()

    Dim oModel As ModelReference

    ' Loop through all models in the active DGN
    For Each oModel In ActiveDesignFile.Models

        ' Only run on sheet models
        If oModel.Type = msdModelTypeSheet Then

            oModel.Activate   ' make this sheet active

            ' Call the recorded macro that does the delete on this sheet
            BmrISD_WK_SH_SR_8

        End If

    Next oModel

    ' Save settings after all changes
    CadInputQueue.SendCommand "FILEDESIGN SAVESETTINGS"

    MsgBox "Finished changing the title on all sheet models.", vbInformation

End Sub
